(defun c:buildlab ()
  (command "ящик" '(0 0 0) "Д" 50 60 20)
  (setq figure (entlast))
  (command "ящик" '(10 0 0) "Д" 40 60 10)
  (command "вычитание" figure "" (entlast) "")
  (command "ящик" '(40 0 20) "Д" 10 30 10)
  (command "объединение" figure (entlast) "")
  (command "3dгрань" '(0 60 20) '(20 60 60) '(20 60 20) "" "")
  (command "выдавить" (entlast) "" -10)
  (command "объединение" figure (entlast) "")
  (command "зеркало" figure "" '(50 0 0) '(50 1 0) "")
  (command "ящик" '(20 30 20) "Д" 60 30 60)
  (command "объединение" figure (entlast) "")
  (command "пск" "X" 90)
  (command "цилиндр" '(50 80 -60) 30 30)
  (command "объединение" figure (entlast) "")
  (command "цилиндр" '(50 80 -60) 10 30)
  (command "пск" "X" -90)
  (command "вычитание" figure "" (entlast) "")
)
