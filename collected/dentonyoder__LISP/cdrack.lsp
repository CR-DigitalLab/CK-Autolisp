(defun updateall()
  	(set_tile "x" (rtos x-var))
	(set_tile "cd" (itoa cd-var))
	(set_tile "dvd" (itoa dvd-var))
	(set_tile "vhs" (itoa vhs-var))
)

(defun c:cdrack ()
  ;;; store defaults to variables
	(setq cd-var 2)
  	(setq dvd-var 3)
  	(setq vhs-var 0)
	(setq x-var 36)

 (setq dcl_id (load_dialog "cdrack.dcl"))
 (if (not (new_dialog "cdrack" dcl_id)) (exit))

  ;;; upload defaults to dialog
	(set_tile "x" (rtos x-var))
	(set_tile "cd" (itoa cd-var))
	(set_tile "dvd" (itoa dvd-var))
	(set_tile "vhs" (itoa vhs-var))

  ;;; read dialog actions
	(action_tile "x" "(setq x-var (distof $value 4)) (updateall)")
	(action_tile "cd" "(setq cd-var (atoi $value)) (updateall)")
	(action_tile "dvd" "(setq dvd-var (atoi $value)) (updateall)")
	(action_tile "vhs" "(setq vhs-var (atoi $value)) (updateall)")

 (action_tile "accept" "(done_dialog 1)")
 (action_tile "cancel" "(done_dialog 0)")

 (setq done_dlg_val (start_dialog))
 (if (= 1 done_dlg_val) (progn
  (prompt "\nUser pressed OK")
  ;;; do the job, it's OK

	(setq p1 (getpoint "\nSelect a lower left point :"))
	(setq x x-var)
  	(setvar "osmode" 0)
  	(setq y (+ (* 6.25 vhs-var) (* 7.5 cd-var) (* 9.5 dvd-var)))
  	(setq y (+ y 3))
  
  	(command "line" p1 (polar p1 (/ pi 2.0) y)
		 (polar (polar p1 (/ pi 2.0) y) 0 x)
		 (polar p1 0 x) "c")
  	(command "line" (polar p1 0 (- x 0.75)) (polar (polar p1 (/ pi 2.0) y) 0 (- x 0.75)) "")
  	(command "line" (polar p1 0 0.75) (polar (polar p1 (/ pi 2.0) y) 0 0.75) "")
  	(command "line" (polar (polar p1 0 0.75) (/ pi 2.0) 0.75)
		 (polar (polar p1 0 (- x 0.75)) (/ pi 2.0) 0.75) "")
  	(command "line" (polar (polar p1 0 0.75) (/ pi 2.0) (- y 0.75))
		 (polar (polar p1 0 (- x 0.75)) (/ pi 2.0) (- y 0.75)) "")

	(setq temp-p1 (polar (polar p1 0 0.75) (/ pi 2.0) 0.75))
  	(setq temp-x (- x 1.5))

  	(setq n 0)
  	(while (< n vhs-var)	;;; loop on vhs shelves front view
	  (command "line" (polar temp-p1 (/ pi 2.0) 0.5)
		   (polar (polar temp-p1 (/ pi 2.0) 0.5) 0 temp-x) "")
	  (command "line" (polar temp-p1 (/ pi 2.0) 5.5)
		   (polar (polar temp-p1 (/ pi 2.0) 5.5) 0 temp-x) "")
	  (command "line" (polar temp-p1 (/ pi 2.0) 6.25)
		   (polar (polar temp-p1 (/ pi 2.0) 6.25) 0 temp-x) "")
	  (setq temp-p1 (polar temp-p1 (/ pi 2.0) 6.25))
	  (setq n (+ n 1))
	  )

	(setq temp-p1 (polar p1 pi 24))	;;; side view
  	(command "line" temp-p1 (polar temp-p1 (/ pi 2.0) y)
		 (polar (polar temp-p1 (/ pi 2.0) y) 0 8.5)
		 (polar temp-p1 0 8.5) "c")
  	(command "line" (polar (polar temp-p1 (/ pi 2.0) y) 0 8.25)
		 (polar temp-p1 0 8.25) "")
  	(command "line" (polar temp-p1 (/ pi 2.0) 0.75)
		 (polar (polar temp-p1 (/ pi 2.0) 0.75) 0 8.25) "")
  	(command "line" (polar temp-p1 (/ pi 2.0) (- y 0.75))
		 (polar (polar temp-p1 (/ pi 2.0) (- y 0.75)) 0 8.25) "")

    	(setq n 0)
  	(setq temp-p1 (polar temp-p1 (/ pi 2.0) 0.75))
  	(while (< n vhs-var)	;;; loop on vhs shelves front view
	  (command "line" (polar temp-p1 (/ pi 2.0) 0.5)
		   (polar (polar temp-p1 (/ pi 2.0) 0.5) 0 0.5)
		   (polar temp-p1 0 0.5) "")
	  (command "line" (polar temp-p1 (/ pi 2.0) 5.5)
		   (polar (polar temp-p1 (/ pi 2.0) 5.5) 0 8.25) "")
	  (command "line" (polar temp-p1 (/ pi 2.0) 6.25)
		   (polar (polar temp-p1 (/ pi 2.0) 6.25) 0 8.25) "")
	  (setq temp-p1 (polar temp-p1 (/ pi 2.0) 6.25))
	  (setq n (+ n 1))
	  )
  
    	(setq n 0)
  	(while (< n cd-var)	;;; loop on cdrack
	  (command "line" (polar (polar temp-p1 (/ pi 2.0) 2.5743) 0 0.5710)
		   (polar (polar temp-p1 (/ pi 2.0) 0.2131) 0 5.8138)
		   (polar (polar temp-p1 (/ pi 2.0) 4.7721) 0 7.867)
		   (polar (polar temp-p1 (/ pi 2.0) 7.1333) 0 2.6242)
		    "c")
	  (command "circle" (polar (polar temp-p1 (/ pi 2.0) 1.82) 0 1.6371) 0.25)
	  (command "circle" (polar (polar temp-p1 (/ pi 2.0) 0.5749) 0 4.4018) 0.25)
	  (command "circle" (polar (polar temp-p1 (/ pi 2.0) 1.1849) 0 6.5257) 0.25)
	  (command "circle" (polar (polar temp-p1 (/ pi 2.0) 3.3968) 0 7.5218) 0.25)
	  (setq temp-p1 (polar temp-p1 (/ pi 2.0) 7.5))
	  (setq n (+ n 1))
	  )


     	(setq n 0)
  	(while (< n dvd-var)	;;; loop on dvd rack
	  (command "line" (polar (polar temp-p1 (/ pi 2.0) 1.8688) 0 0.2686)
		   (polar (polar temp-p1 (/ pi 2.0) 0.3374) 0 5.8109)
		   (polar (polar temp-p1 (/ pi 2.0) 8.0484) 0 7.9416)
		   (polar (polar temp-p1 (/ pi 2.0) 9.5799) 0 2.3993)
		    "c")
	  (command "circle" (polar (polar temp-p1 (/ pi 2.0) 1.2865) 0 1.4375) 0.25)
	  (command "circle" (polar (polar temp-p1 (/ pi 2.0) 0.4789) 0 4.3602) 0.25)
	  (command "circle" (polar (polar temp-p1 (/ pi 2.0) 1.4066) 0 6.3658) 0.25)
	  (command "circle" (polar (polar temp-p1 (/ pi 2.0) 3.7449) 0 7.0118) 0.25)
	  (command "circle" (polar (polar temp-p1 (/ pi 2.0) 6.0831) 0 7.6578) 0.25)
	  (setq temp-p1 (polar temp-p1 (/ pi 2.0) 9.5))
	  (setq n (+ n 1))
	  )

  	;;;; 3d view
  	

  	(setq temp-p1 (polar p1 0 (+ x 48)))
  	(command "pline" temp-p1 (polar temp-p1 (/ pi 2.0) y)
		 (polar (polar temp-p1 (/ pi 2.0) y) 0 8.25)
		 (polar temp-p1 0 8.25) "c")
  	(command "zoom" "e" "zoom" "0.8x")
  	(command "extrude" "l" "" -0.75 0)

  	(setq e1 (entlast))
  
  	(command "copy" "l" "" "0,0,0" (list 0 0 (- x 0.75)))
   	(command "pline" (polar temp-p1 0 8.25)
		 (polar (polar temp-p1 (/ pi 2.0) y) 0 8.25)
		 (polar (polar temp-p1 (/ pi 2.0) y) 0 8.5)
		 (polar temp-p1 0 8.5) "c")
  	(command "extrude" "l" "" x 0)
  	(command "move" "l" "" "0,0,-0.75" "")
 
  	(command "pline" (polar temp-p1 (/ pi 2.0) y)
		 (polar (polar temp-p1 (/ pi 2.0) y) 0 8.25)
		 (polar (polar temp-p1 (/ pi 2.0) (- y 0.75)) 0 8.25)
		 (polar temp-p1 (/ pi 2.0) (- y 0.75)) "c")
  	(command "extrude" "l" "" (- x 1.5) 0)
  	(command "copy" "l" "" (list 0 (- y 0.75) 0) "0,0,0")

  
    	(setq n 0)
  	(setq temp-p1 (polar temp-p1 (/ pi 2.0) 0.75))
  	(while (< n vhs-var)	;;; loop on vhs shelves front view
	  (command "pline" temp-p1 (polar temp-p1 (/ pi 2.0) 0.5)
		   (polar (polar temp-p1 (/ pi 2.0) 0.5) 0 0.5)
		   (polar temp-p1 0 0.5) "c")
	  (command "extrude" "l" "" (- x 1.5) 0)
	  (command "pline" (polar temp-p1 (/ pi 2.0) 5.5)
		   (polar (polar temp-p1 (/ pi 2.0) 5.5) 0 8.25)
		   (polar (polar temp-p1 (/ pi 2.0) 6.25) 0 8.25)
		   (polar temp-p1 (/ pi 2.0) 6.25) "c")
	  (command "extrude" "l" "" (- x 1.5) 0)
	  (command "pline" (polar temp-p1 0 0.5)  ;;; tape cartridge
		   (polar (polar temp-p1 (/ pi 2.0) 4.125) 0 0.5)
		   (polar (polar temp-p1 (/ pi 2.0) 4.125) 0 8)
		   (polar temp-p1 0 8) "c")
	  (command "extrude" "l" "" 1 0)
		   
	  (setq temp-p1 (polar temp-p1 (/ pi 2.0) 6.25))
	  (setq n (+ n 1))
	  )
  
    	(setq n 0)
  	(while (< n cd-var)	;;; loop on cdrack
	  (command "pline" (polar (polar temp-p1 (/ pi 2.0) 2.5743) 0 0.5710)
		   (polar (polar temp-p1 (/ pi 2.0) 0.2131) 0 5.8138)
		   (polar (polar temp-p1 (/ pi 2.0) 4.7721) 0 7.867)
		   (polar (polar temp-p1 (/ pi 2.0) 7.1333) 0 2.6242)
		    "c")
	  (command "extrude" "l" "" 0.42 0)
	  (command "circle" (polar (polar temp-p1 (/ pi 2.0) 1.82) 0 1.6371) 0.25)
	  (command "extrude" "l" "" (- x 1.5) 0)
	  (command "circle" (polar (polar temp-p1 (/ pi 2.0) 0.5749) 0 4.4018) 0.25)
	  (command "extrude" "l" "" (- x 1.5) 0)
	  (command "circle" (polar (polar temp-p1 (/ pi 2.0) 1.1849) 0 6.5257) 0.25)
	  (command "extrude" "l" "" (- x 1.5) 0)
	  (command "circle" (polar (polar temp-p1 (/ pi 2.0) 3.3968) 0 7.5218) 0.25)
	  (command "extrude" "l" "" (- x 1.5) 0)
	  (setq temp-p1 (polar temp-p1 (/ pi 2.0) 7.5))
	  (setq n (+ n 1))
	  )


     	(setq n 0)
  	(while (< n dvd-var)	;;; loop on dvd rack
	  (command "pline" (polar (polar temp-p1 (/ pi 2.0) 1.8688) 0 0.2686)
		   (polar (polar temp-p1 (/ pi 2.0) 0.3374) 0 5.8109)
		   (polar (polar temp-p1 (/ pi 2.0) 8.0484) 0 7.9416)
		   (polar (polar temp-p1 (/ pi 2.0) 9.5799) 0 2.3993)
		    "c")
	  (command "extrude" "l" "" 0.45 0)
	  (command "circle" (polar (polar temp-p1 (/ pi 2.0) 1.2865) 0 1.4375) 0.25)
	  (command "extrude" "l" "" (- x 1.5) 0)
	  (command "circle" (polar (polar temp-p1 (/ pi 2.0) 0.4789) 0 4.3602) 0.25)
	  (command "extrude" "l" "" (- x 1.5) 0)
	  (command "circle" (polar (polar temp-p1 (/ pi 2.0) 1.4066) 0 6.3658) 0.25)
	  (command "extrude" "l" "" (- x 1.5) 0)
	  (command "circle" (polar (polar temp-p1 (/ pi 2.0) 3.7449) 0 7.0118) 0.25)
	  (command "extrude" "l" "" (- x 1.5) 0)
	  (command "circle" (polar (polar temp-p1 (/ pi 2.0) 6.0831) 0 7.6578) 0.25)
	  (command "extrude" "l" "" (- x 1.5) 0)
	  (setq temp-p1 (polar temp-p1 (/ pi 2.0) 9.5))
	  (setq n (+ n 1))
	  )

   (setq p1 (polar p1 0 (+ x 48)))
    	(setq edsifirst e1)
	(setq edsiss nil)
	(setq edsiss (ssadd edsifirst))
	(setq edsifirst (entnext edsifirst))
	(while (/= edsifirst nil)
	  (ssadd edsifirst edsiss)
	  (setq edsifirst (entnext edsifirst))
	  )
   (command "move" edsiss "" "0,0,0" "0,0,0")
  
   (command "ucs" "o" p1)
   (command "ucs" "x" "-90")
   (command "Rotate" "p" "" (list 0 0 0) "45")
   (command "ucs" "p")
   (command "ucs" "y" "90")
   (command "rotate" "p" "" (list 0 0 0) "30")
   (command "ucs" "w")
   (command "redraw")


  
 )
  (prompt "\nUSER PRESSED CANCEL")
 )
(unload_dialog dcl_id)
 (prin1)
)
