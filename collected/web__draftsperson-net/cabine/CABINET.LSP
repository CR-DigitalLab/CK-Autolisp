; FILE NAME: CABINET.LSP
; Written by: Bob Thomas                
;             Thomas Enterprises, ltd.  
;             1030 "B" Street, Suite 201
;             San Rafael, CA 94901   
;             415/453-8712
;
; This file and its accompanying Release 10 drawing file, CABINET.DWG, may be 
; freely copied provided that the two files remain together and this header 
; remains intact, so that people know what the program does and I can get a 
; free plug in. Thank you.  Use and enjoy...
;
; Recommended LISPSTACK=40000   LISPHEAP=5000, or R10 Extended AutoLISP
;
; This file contains a parametric program that creates 2D representations of
; cabinet faces.  All variables are local except those used to set and retain 
; defaults, as follows (Rename these if they conflict with yours):
;
;  bcw   = Cabinet width (24")
;  bch   = Cabinet height (36")
;          (72" for linen cabinets, if no height value entered previously)
;  oset1 = 1st offset (drawer-to-side: 2")
;  oset2 = 2nd offset (drawer detail: 1")
;  bth   = Base trim height (4")
;  bto   = Base trim offset (1")
;  dc    = Drawer configuration (4)
;  nd    = Number of drawers (1)
;
;  (All values entered become default for repeats.)
;
; AutoCAD Command Prompt Sequence:
;
; Command: CABINET
;   Basic/Linen/Wall:                (Select one)
;   Cabinet width: <default>:        (Enter)
;   Height <default>:                (Enter)
;   Base trim height <default>:      (Basic & linen cabinets)
;   Base trim offset <default>:      (Basic & linen cabinets)
;   Base cabinet height <default>:   (Linen cabinets only)
;   1st offset <default>:            (Space btw. drawers and side)
;   2nd offset <default>:            (Drawer detail offset)
;   Drawer Configuration <default>:  (Max. number of drawers; determines size)
;   Number of drawers <default>:     (Actual drawers this cabinet)
;   Move cabinet into place.         (When outline is drawn, position cabinet)
;
;   The accompanying Release 9 drawing file, CABINET.DWG, illustrates the
;   drawing parameters that correspond to these prompts.
;
(prompt "\nLoading CABINET.LSP...")
(defun C:CABINET( / c x xbch xbcw xbth xbto xoset1 xoset2 xdc xnd i_pt olderr
  oldblp oldcmd oldort atest gt dipt dcpt fdipt idipt dipt2 dipt3 dipt4 idipt2
  idipt3 idipt4 ss1 ss2 ss3 up down across valid linen basic wall ctype)
   (setq oldblp (getvar "BLIPMODE") oldcmd (getvar "CMDECHO")
         olderr *ERROR* oldort (getvar "ORTHOMODE") down 4.712389 gt " <"
         ss1 (ssadd) x ">: " i_pt (cadr (grread 12)) up 1.570796 c "c"
         basic nil linen nil wall nil valid nil)
   (defun *ERROR* (msg) (princ msg) (setvar "BLIPMODE" oldblp)
     (setvar "CMDECHO" oldcmd) (setvar "ORTHOMODE" oldort)
     (setq *ERROR* olderr) (princ))
   (setvar "BLIPMODE" 0) (setvar "CMDECHO" 0)
   (if (= bth nil)   (setq bth 4))   (if (= bto nil)   (setq bto 1))
   (if (= oset1 nil) (setq oset1 2)) (if (= oset2 nil) (setq oset2 1))
   (if (= dc nil)    (setq dc 4))    (if (= nd nil)    (setq nd 1))
   (if (= bcw nil)   (setq bcw 24))  (if (= bbch nil)  (setq bbch 36))
   (while (and (not basic) (not linen) (not wall))
     (setq ctype (strcase (substr (getstring "Basic/Linen/Wall: ") 1 1)))
     (cond ((= ctype "B") (setq basic T)) ((= ctype "L") (setq linen T))
           ((= ctype "W") (setq wall T))))
   (if (and (= bch nil) (/= ctype "L")) (setq bch 36))
   (if (and (= bch nil) (= ctype "L")) (setq bch 72))
   (if (= ctype "L") (setq linen T) (setq linen nil))
   (while (not valid)
    (setq xbcw (getdist (strcat "\nCabinet width" gt (rtos bcw) x)))
    (if (or (= xbcw nil) (= xbcw "")) (eval nil) (setq bcw xbcw))
    (setq xbch (getdist (strcat "\nHeight" gt (rtos bch) x)))
    (if (or (= xbch nil) (= xbch "")) (eval nil) (setq bch xbch))
    (if (not wall) (progn
      (setq xbth (getdist (strcat "\nBase trim height" gt (rtos bth) x)))
      (if (or (= xbth nil) (= xbth "")) (eval nil) (setq bth xbth))
      (setq xbto (getdist (strcat "\nBase trim offset" gt (rtos bto) x)))
      (if (or (= xbto nil) (= xbto "")) (eval nil) (setq bto xbto))))
      (setq xoset1 (getdist (strcat "\n1st offset" gt (rtos oset1) x)))
      (if (or (= xoset1 nil) (= xoset1 "")) (eval nil) (setq oset1 xoset1))
      (setq xoset2 (getdist (strcat "\n2nd offset" gt (rtos oset2) x)))
      (if (or (= xoset2 nil) (= xoset2 "")) (eval nil) (setq oset2 xoset2))
      (if linen (progn
       (setq xbbch (getdist (strcat "\nBase cabinet height" gt (rtos bbch) x)))
       (if (or (not xbbch) (= xbbch "")) (eval nil) (setq bbch xbbch))))
      (if wall (setq valid T) (progn
       (setq xdc (getint (strcat "\nDrawer configuration" gt (rtos dc 2 0) x)))
       (if (or (= xdc nil) (= xdc "")) (eval nil) (setq dc xdc))
        (setq xnd (getint (strcat "\nNumber of drawers" gt (rtos nd 2 0) x)))
        (if (or (= xnd nil) (= xnd "")) (eval nil) (setq nd xnd))
        (setq dtest 1 across 1 atest 1)
        (if (= linen T)
           (setq dcw (- bcw (* 2 oset1))
                 dch (- (- bch (* 2 oset1)) bth)
                 dh  (/ (- dch (+ bbch (* oset1 dc))) (float dc))
                 fdh (+ (* dh (- dc nd)) (* oset1 (1- (- dc nd)))))
           (setq dcw (- bcw (* 2 oset1))
                 dch (- (- bch (* 2 oset1)) bth)
                 dh  (/ (- dch (* oset1 (1- dc))) (float dc))
                 fdh (+ (* dh (- dc nd)) (* oset1 (1- (- dc nd))))))
        (if (< dh 0)
         (prompt (strcat "\nImpossible cabinet. Drawer: " (rtos dh 2 0)))
         (progn (prompt "\nProcessing. One moment...") (setq valid T))))))
   (if (not wall) (progn
       (while (> dcw 24)
          (setq across (1+ across)
                dcw (/ (- bcw (* oset1 (1+ across))) (float across))))
       (command "pline" i_pt "w" 0 0 (polar i_pt up bch)
                (polar (getvar "LASTPOINT") 0 bcw)
                (polar (getvar "LASTPOINT") down bch) c)
       (setq ss1 (ssadd (entlast)))
       (command "line" (polar i_pt up bth) 
                (polar (getvar "LASTPOINT") 0 bcw) "")
       (setq ss1 (ssadd (entlast) ss1))
       (command "line" (polar i_pt up (- bth bto)) 
                (polar (getvar "LASTPOINT") 0 bcw) "")
       (setq ss1 (ssadd (entlast) ss1))
       (setvar "ORTHOMODE" 0)
       (prompt "\nMove cabinet into place.")
       (command "move" ss1 "" i_pt pause)
       (setq i_pt2 (getvar "lastpoint")
             dipt (polar (polar (polar i_pt2 up bch) 0 oset1) down oset1))
       (if basic (setq dcpt (polar dipt down (+ dh oset1))))
         (if linen (progn
            (command "pline" dipt (setq dipt2 (polar dipt 0 dcw))
                     (setq dipt3 (polar dipt2 down bbch))
                     (setq dipt4 (polar dipt3 pi dcw)) c)
            (setq ss3 (ssadd (entlast)))
            (command "pline" (setq idipt (polar (polar dipt 0 oset2) 
                                                down oset2))
                     (setq idipt2 (polar idipt 0 (- dcw (* oset2 2))))
                     (setq idipt3 (polar idipt2 down (- bbch (* oset2 2))))
                     (setq idipt4 (polar idipt3 pi (- dcw (* oset2 2)))) c)
            (setq ss3 (ssadd (entlast) ss3))
            (command "line" dipt idipt "")
            (setq ss3 (ssadd (entlast) ss3))
            (command "line" dipt2 idipt2 "")
            (setq ss3 (ssadd (entlast) ss3))
            (command "line" dipt3 idipt3 "")
            (setq ss3 (ssadd (entlast) ss3))
            (command "line" dipt4 idipt4 "")
            (setq ss3 (ssadd (entlast) ss3))
            (setq udipt dipt
                  dipt (polar dipt down (+ bbch oset1))
                  dcpt (polar dipt down (+ dh oset1)))))
         (command "pline" dipt (setq dipt2 (polar dipt 0 dcw))
                  (setq dipt3 (polar dipt2 down dh))
                  (setq dipt4 (polar dipt3 pi dcw)) c)
         (setq ss1 (ssadd (entlast)))
         (command "pline" (setq idipt (polar (polar dipt 0 oset2) down oset2))
                  (setq idipt2 (polar idipt 0 (- dcw (* oset2 2))))
                  (setq idipt3 (polar idipt2 down (- dh (* oset2 2))))
                  (setq idipt4 (polar idipt3 pi (- dcw (* oset2 2)))) c)        
         (setq ss1 (ssadd (entlast) ss1))
         (command "line" dipt idipt "")
         (setq ss1 (ssadd (entlast) ss1))
         (command "line" dipt2 idipt2 "")
         (setq ss1 (ssadd (entlast) ss1))
         (command "line" dipt3 idipt3 "")
         (setq ss1 (ssadd (entlast) ss1))
         (command "line" dipt4 idipt4 "")
         (setq ss1 (ssadd (entlast) ss1))
         (while (< dtest nd)
             (command "copy" ss1 "" dipt dcpt)
             (setq dtest (1+ dtest) dcpt (polar dcpt down (+ dh oset1))))
             (if (< nd dc) (progn
               (setq fdipt dcpt)
               (command "pline" dcpt (setq dipt2 (polar dcpt 0 dcw))
                      (setq dipt3 (polar dipt2 down fdh))
                      (setq dipt4 (polar dipt3 pi dcw)) c)
                      (setq ss2 (ssadd (entlast)))
               (command "pline" (setq idipt (polar (polar dcpt 0 oset2) 
                                                down oset2))
                      (setq idipt2 (polar idipt 0 (- dcw (* oset2 2))))
                      (setq idipt3 (polar idipt2 down (- fdh (* oset2 2))))
                      (setq idipt4 (polar idipt3 pi (- dcw (* oset2 2)))) c)
               (setq ss2 (ssadd (entlast) ss2))
               (command "line" dcpt idipt "")
               (setq ss2 (ssadd (entlast) ss2))
               (command "line" dipt2 idipt2 "")
               (setq ss2 (ssadd (entlast) ss2))
               (command "line" dipt3 idipt3 "")
               (setq ss2 (ssadd (entlast) ss2))
               (command "line" dipt4 idipt4 "")
               (setq ss2 (ssadd (entlast) ss2))))
         (while (< atest across)
            (if linen (progn
               (setq dcpt (polar udipt 0 (* (+ dcw oset1) atest)))
               (command "copy" ss3 "" udipt dcpt)))
            (setq dcpt (polar dipt 0 (* (+ dcw oset1) atest))
                  atest (1+ atest) dtest 1)
            (while (<= dtest nd)
               (command "copy" ss1 "" dipt dcpt)
               (setq dtest (1+ dtest) dcpt (polar dcpt down (+ dh oset1))))
            (if (< nd dc) (progn
               (setq dcpt (polar fdipt 0 (* (+ dcw oset1) (1- atest))))
               (command "copy" ss2 "" fdipt dcpt)))))
      (progn
         (command "pline" i_pt "w" 0 0 (polar i_pt 0 bcw)
            (polar (getvar "LASTPOINT") down bch)
            (polar (getvar "LASTPOINT") pi bcw) c)
         (setq ss1 (ssadd (entlast))
               h (- bch (* oset1 2))
               w (- bcw (* oset1 2)))
         (command "pline" (setq dipt (polar (polar i_pt 0 oset1) down oset1))
            (setq dipt2 (polar dipt 0 w)) (setq dipt3 (polar dipt2 down h))
            (setq dipt4 (polar dipt3 pi w)) c)
         (setq ss1 (ssadd (entlast) ss1)
               h (- h (* oset2 2))
               w (- w (* oset2 2)))
         (command "pline" (setq idipt (polar (polar i_pt 0 (+ oset1 oset2))
                                             down (+ oset1 oset2)))
                  (setq idipt2 (polar idipt 0 w))
                  (setq idipt3 (polar idipt2 down h))
                  (setq idipt4 (polar idipt3 pi w)) c)
         (setq ss1 (ssadd (entlast) ss1))
         (command "line" dipt idipt "")
         (setq ss1 (ssadd (entlast) ss1))
         (command "line" dipt2 idipt2 "")
         (setq ss1 (ssadd (entlast) ss1))
         (command "line" dipt3 idipt3 "")
         (setq ss1 (ssadd (entlast) ss1))
         (command "line" dipt4 idipt4 "")
         (setq ss1 (ssadd (entlast) ss1))
         (setvar "ORTHOMODE" 0)
         (prompt "\nMove cabinet into place.")
         (command "move" ss1 "" i_pt pause)))
   (setvar "BLIPMODE" oldblp)
   (setvar "CMDECHO" oldcmd)
   (setvar "ORTHOMODE" oldort)
   (setq *ERROR* olderr)
   (prompt "\nCabinet complete.")
   (princ))
(prompt "Loaded.\n")
(princ)
; EOF:   Cabinet.LSP     239 lines      Bob Thomas
