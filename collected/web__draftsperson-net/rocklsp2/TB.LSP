;   Terminal Block constructor
   ;   Copyright 1990   Rocket Software
   ;   AutoCad as a spectator sport - it's more fun to watch TB run
   ;   than it is to draw terminal blocks.  Also TB is faster.
 (defun C:TB ( / acc nt incr num pta ptb vdist tt fh txht txp pta1 ptb1)
   (setvar "cmdecho" 0)
   (setq acc 0)
   (setq nt (getint "Start # <1>: "))
   (if (null nt) (setq nt 1))
   (setq incr (getint "\nIncrement (negative numbers are OK) <1>: "))
   (if (null incr) (setq incr 1))
   (setq num (getint "\nNumber of terminals: "))
   (setq pta (getpoint "\nTop line start: "))
   (setq ptb (getpoint pta "And end:"))
   (setq vdist (getdist ptb "\nVertical spacing <5>:"))
   (if (null vdist) (setq vdist 5.0))
   (setq tt (getvar "textstyle"))
   (setq fh (cdr (assoc 40 (tblsearch "style" tt))))
   (if (= fh 0.0)
       (progn
             (setq txht (getdist ptb "\nText Height <2.5>:"))
             (if (null txht) (setq txht 2.5))))
   (setq txp (list (/ (+ (car pta) (car ptb)) 2) (- (cadr pta) (/ vdist 2))))
   (setq pta1 (list (car pta) (- (cadr pta) (* num vdist))))
   (setq ptb1 (list (car ptb) (- (cadr ptb) (* num vdist))))
   (command "line" pta1 pta ptb ptb1 "")
   (WHILE (> num acc)
          (setq numt (itoa nt))
          (setq acc (1+ acc))
          (if (= fh 0.0)
              (command "text" "m" txp txht "" numt)
              (command "text" "m" txp "" numt))
          (setq txp (list (car txp) (- (cadr txp) vdist)))
          (setq pta (list (car pta) (- (cadr pta) vdist)))
          (setq ptb (list (car ptb) (- (cadr ptb) vdist)))
          (command "line" pta ptb "")
          (setq nt (+ incr nt))
   )
  (PRINC))
