;  Snapper - put entities back on snap
  ;  ...sometimes at the expense of interconnectedness...
  ;  Copyright 1990   Rocket Software
  ;  - Software of last resort.
  (DEFUN C:SNAPPER ( / oth ss aa bb cc txa nn yy dx dfx dy dfy dd)
  (setvar "cmdecho" 0)
  (setq oth (getvar "orthomode"))
  (setvar "orthomode" 0)
  (SETQ SS (SSGET))
  (setq aa (getvar "snapunit"))
  (setq bb (car aa) cc (cadr aa))
  (WHILE (SETQ TXA (SSNAME SS 0))
         (SETQ NN (ENTGET TXA))
         (IF (and (= (cdr (assoc 0 nn)) "TEXT")
                  (or (= (cdr (assoc 72 nn)) 2)
                      (= (cdr (assoc 72 nn)) 4)
                      (= (cdr (assoc 72 nn)) 1)))
             (progn
                   (SETQ YY (cdr (ASSOC 11 NN)))
                   (setq dx (rem (car yy) bb))
                   (setq dy (rem (cadr yy) cc))
                   (setq dfx (abs (- bb dx))) 
                   (setq dfy (abs (- cc dy))) 
                   (if (< dfx (/ bb 2))
                       (setq dx (- dx bb)))
                   (if (< dfy (/ cc 2))
                       (setq dy (- dy cc)))
                   (setq dd (list dx dy))
                   (command "move" txa "" dd "0,0"))
             (progn
                   (SETQ YY (cdr (ASSOC 10 NN)))
                   (setq dx (rem (car yy) bb))
                   (setq dy (rem (cadr yy) cc))
                   (setq dfx (abs (- bb dx))) 
                   (setq dfy (abs (- cc dy))) 
                   (if (< dfx (/ bb 2))
                       (setq dx (- dx bb)))
                   (if (< dfy (/ cc 2))
                       (setq dy (- dy cc)))
                   (setq dd (list dx dy))
                   (command "move" txa "" dd "0,0")))
         (SSdel TXA SS))
  (SETQ SS NIL)
  (setvar "orthomode" oth)
  (PRINC))
