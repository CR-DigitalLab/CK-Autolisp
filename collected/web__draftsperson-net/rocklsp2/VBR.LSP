;  Venetian Blind (Right)
   ;  Multiple text rejustifier.
   ;  Copyright 1991  Rocket Software
 (defun C:VBR ( / ss xa num txa nn yy zz st styl fh hh tt)
  (command "undo" "mark")
  (setvar "cmdecho" 0)
  (prompt "Pick text strings:")
  (setq ss (ssget)
        xa (car (getpoint "\nPick start:"))
        num 0
        tt (getvar "textstyle")
        fh (cdr (assoc 40 (tblsearch "style" tt))))
  (while (setq txa (ssname ss 0)) (setq nn (entget txa))
         (if (= (cdr (assoc 0 nn)) "TEXT")
             (progn (setq yy (cddr (assoc 10 nn))
                          zz (cdr (assoc 1 nn))
                          num (1+ num)
                          styl (cdr (assoc 7 nn))
                          hh (cdr (assoc 40 nn))
                          st (cons xa yy ))
                    (entdel txa)
                    (if (= fh 0.0)
                        (command "text" "r" st hh "" zz)
                        (command "text" "r" st "" zz ))))
         (ssdel txa ss))
   (setq ss nil)
   (if (> num 0)
       (progn    
             (if (= num 1)
                 (prompt "\n1 line right justified.")
                 (prompt (strcat "\n" (ITOA num) " lines right justified."))
             )
       )
   )
 (PRINC))
