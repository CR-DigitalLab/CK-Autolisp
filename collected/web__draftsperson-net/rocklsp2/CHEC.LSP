; CHEC - Multiple recursive (cyclic) artifact/noise file integrity test.
 ; by SW for Rocket Software  Copyright 1991
 ; Impress your co-workers and superiors, show your computer who's boss.
 (DEFUN C:CHEC ( / pa p1 nn num tt fh aa bb cc dd ee xx tx ttt
                         ty na nb nc nd ne naa nbb ncc ndd nee)
  (setq tt (getvar "textstyle"))
  (setq fh (cdr (assoc 40 (tblsearch "style" tt))))
  (setvar "cmdecho" 0)
  (setq pa (setq p1 (getpoint "\nPick start:")))
  (setq nn (getint "\nBitcheck recursion factor <12>: "))
  (if (null nn) (setq nn 12))
  (setq tx (+ (car pa) 5) ty (- (cadr pa) 4))
  (setq pa (list tx ty))
  (if (= fh 0.0)
      (command "text" pa "3" "" "00000")
      (command "text" pa "" "00000"))
  (setq aa (entget (entlast)))
  (setq naa 10001)
  (grclear)
  (command "insert" "chec" p1 "" "" "")
  (setq xx (entlast))
  (if (= fh 0.0)
      (setq ttt '(progn 
                       (setq ty (- (cadr pa) 5))
                       (setq pa (list tx ty))
                       (command "text" pa "3" "" "00000")))
      (setq ttt '(progn
                       (setq ty (- (cadr pa) 5))
                       (setq pa (list tx ty))
                       (command "text" pa "" "00000"))))

  (eval ttt)
  (setq bb (entget (entlast)))
  (setq nbb 1121)
  (eval ttt)
  (setq cc (entget (entlast)))
  (setq ncc 16)
  (eval ttt)
  (setq dd (entget (entlast)))
  (setq ndd 21000)
  (eval ttt)
  (setq ee (entget (entlast)))
  (setq nee 13471)
  (setq num 1)
  (WHILE (< num nn)
         (setq num (1+ num))
         (setq naa (1+ naa))
         (setq nbb (+ 3 nbb))
         (setq ncc (+ 16 ncc))
         (setq ndd (1+ ndd))
         (setq nee (+ 2 nee))
         (setq na (itoa (fix naa)))
         (entmod (subst (cons 1 na) (assoc 1 aa) aa))
         (setq nd (itoa (fix ndd)))
         (entmod (subst (cons 1 nd) (assoc 1 dd) dd))
         (setq nb (itoa (fix nbb)))
         (entmod (subst (cons 1 nb) (assoc 1 bb) bb))         
         (setq ndd (+ 2 ndd))
         (setq nd (itoa (fix ndd)))
         (entmod (subst (cons 1 nd) (assoc 1 dd) dd))
         (setq nc (itoa (fix ncc)))
         (entmod (subst (cons 1 nc) (assoc 1 cc) cc))
         (setq ne (itoa (fix nee)))
         (entmod (subst (cons 1 ne) (assoc 1 ee) ee))
  )
  (entdel xx)
  (entdel (cdar aa))
  (entdel (cdar bb))
  (entdel (cdar cc))
  (entdel (cdar dd))
  (entdel (cdar ee))
  (redraw)
  (write-line (strcat (itoa nn) " recursions OK "))
  (PRINC))
