;  Venetian Blind (Middle)
   ;  Multiple text rejustifier.
   ;  Copyright 1991  Rocket Software
 (DEFUN C:VBM ( / ss cc ee xa tt num txa nn yy zz st styl fh hh)
  (command "undo" "mark")
  (setvar "cmdecho" 0)
  (prompt "Pick text strings:")
  (setq ss (ssget)
        cc (getpoint "\nPick one side:"))
  (setq ee (getpoint cc "\n...and the other:"))
  (setq xa (/ (+ (car cc) (car ee)) 2) 
        num 0)
  (setq tt (getvar "textstyle"))
  (while (setq txa (ssname ss 0)) (setq nn (entget txa))
         (if (= (cdr (assoc 0 nn)) "TEXT")
             (progn (setq yy (cddr (assoc 10 nn))
                          zz (cdr (assoc 1 nn))
                          num (1+ num)
                          styl (cdr (assoc 7 nn))
                          hh (cdr (assoc 40 nn))
                          st (cons xa yy ))
                    (setq fh (cdr (assoc 40 (tblsearch "style" tt))))
                    (entdel txa)
                    (if (= fh 0.0)
                        (command "text" "m" st hh "" zz)
                        (command "text" "m" st "" zz ))))
         (ssdel txa ss))
   (setq ss nil)
   (if (> num 0)
       (progn    
             (if (= num 1)
                 (prompt "\n 1 line rejustified.")
                 (prompt (strcat "\n" (itoa num) " lines rejustified."))
             )
       )
   )
 (PRINC))
