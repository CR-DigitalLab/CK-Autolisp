;   Terminal Block constructor
   ;   (with prefix and suffix and angles - now stop bitching).
   ;   Copyright 1990   Rocket Software
 (defun C:TBTX ( / acc nt pref suff ang angg incr
                   num pta ptb vdist txht txp pta1 ptb1)
   (setvar "cmdecho" 0)
   (setq acc 0)
   (setq nt (getint "Start # <1>: "))
   (setq pref (getstring t "\nPrefix text <zilch>: "))
   (setq suff (getstring t "\nSuffix text <zip>: "))
   (if (null nt) (setq nt 1))
   (setq incr (getint "\nIncrement (negative numbers are OK) <1>: "))
   (if (null incr) (setq incr 1))
   (setq num (getint "\nNumber of terminals: "))
   (setq pta (getpoint "\nTop line start: "))
   (setq hdist (getdist pta "\nAnd length: "))
   (setq vdist (getdist pta "\nVertical spacing <5>: "))
   (setq ang (getangle pta "\nTerminal block angle: "))
   (setq angg (getangle pta "\nText angle <Match block angle>: "))
   (if (null angg)
       (setq angg (+ 90 (* (/ 180 pi) ang)))
       (setq angg (* (/ 180 pi) angg)))
   (setq ptb (polar pta (+ (/ pi 2) ang) hdist))
   (if (null vdist) (setq vdist 5.0))
   (setq tt (getvar "textstyle"))
   (setq fh (cdr (assoc 40 (tblsearch "style" tt))))
   (if (= fh 0.0)
       (progn
             (setq txht (getdist pta "\nText Height <2.5>:"))
             (if (null txht) (setq txht 2.5)))
       (write-line "\nFixed height text?  You use fixed height text?"))
   (setq txp (polar (polar pta (+ (/ pi 2) ang) (/ hdist 2)) ang (/ vdist 2)))
   (setq pta1 (polar pta ang (* num vdist)))
   (setq ptb1 (polar ptb ang (* num vdist)))
   (command "line" pta1 pta ptb ptb1 "")
   (WHILE (> num acc)
          (setq numt (strcat pref (itoa nt) suff))     ; add prefix and suffix
          (setq acc (1+ acc))
          (if (= fh 0.0)
              (command "text" "m" txp txht angg numt)
              (command "text" "m" txp angg numt))
          (setq txp (polar txp ang vdist))
          (setq pta (polar pta ang vdist))
          (setq ptb (polar ptb ang vdist))
          (command "line" pta ptb "")
          (setq nt (+ incr nt))
   )
  (PRINC))
