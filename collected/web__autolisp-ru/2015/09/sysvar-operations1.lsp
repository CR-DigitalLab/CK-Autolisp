(vl-load-com)

(setq *global-sysvar-list* '((("name" . "*_toolpalettepath") ("ver" . "2009,2010,2011,2012,2013,2014,2015,2016"))
                             (("name" . "3dconversionmode") ("ver" . "2009,2010,2011,2012,2013,2014,2015,2016"))
                             (("name" . "3ddwfprec") ("ver" . "2009,2010,2011,2012,2013,2014,2015,2016"))
                             (("name" . "3dosmode") ("ver" . "2011,2012,2013,2014,2015,2016"))
                             (("name" . "3dosnap") ("ver" . "2011"))
                             (("name" . "3dselectionmode") ("ver" . "2009,2010,2011,2012,2013,2014,2015,2016"))
                             (("name" . "_pkser") ("ver" . "2009,2010,2011,2012,2013,2014,2015,2016"))
                             (("name" . "_server") ("ver" . "2009,2010,2011,2012,2013,2014,2015,2016"))
                             (("name" . "_toolpalettepath") ("ver" . "2009,2010,2011,2012,2013,2014,2015,2016"))
                             (("name" . "_vernum") ("ver" . "2009,2010,2011,2012,2013,2014,2015,2016"))
                             (("name" . "acadlspasdoc") ("ver" . "2009,2010,2011,2012,2013,2014,2015,2016"))
                             (("name" . "acadprefix") ("ver" . "2009,2010,2011,2012,2013,2014,2015,2016"))
                             (("name" . "acadver") ("ver" . "2009,2010,2011,2012,2013,2014,2015,2016"))
                             (("name" . "acisoutver") ("ver" . "2009,2010,2011,2012"))
                             (("name" . "actpath") ("ver" . "2009,2010,2011,2012,2013,2014,2015,2016"))
                             (("name" . "actrecorderstate") ("ver" . "2009,2010,2011,2012,2013,2014,2015,2016"))
                             (("name" . "actrecpath") ("ver" . "2009,2010,2011,2012,2013,2014,2015,2016"))
                             (("name" . "actui") ("ver" . "2009,2010,2011,2012,2013,2014,2015,2016"))
                             (("name" . "adcstate") ("ver" . "2009,2010,2011,2012,2013,2014,2015,2016"))
                             (("name" . "aec3ddwfedge") ("ver" . "2012,2013,2014,2015,2016"))
                             (("name" . "aeceipinprogress") ("ver" . "2010,2011,2012,2013,2014,2015,2016"))
                             (("name" . "aecenableassocanchor") ("ver" . "2015,2016"))
                             (("name" . "aecenablesectioncleanup") ("ver" . "2015,2016"))
                             (("name" . "aecforcedefaultmodelview") ("ver" . "2012,2013,2014,2015,2016"))
                             (("name" . "aecforcedisplaybysizedisabled") ("ver" . "2012,2013,2014,2015,2016"))
                             (("name" . "aecforceexplodetosolid") ("ver" . "2012,2013,2014,2015,2016"))
                             (("name" . "aecobjectisolatemode") ("ver" . "2013,2014,2015,2016"))
                             (("name" . "aecpsdautoattach") ("ver" . "2014,2015,2016"))
                             (("name" . "aecpsdvisibility") ("ver" . "2016"))
                             (("name" . "aecvcompareignorehatch") ("ver" . "2015,2016"))
                             (("name" . "aecvcompareignoretext") ("ver" . "2015,2016"))
                             (("name" . "aecvcomparenewcolor") ("ver" . "2015,2016"))
                             (("name" . "aecvcompareoldcolor") ("ver" . "2015,2016"))
                             (("name" . "aecvcompareunchangedcolor") ("ver" . "2015,2016"))
                             (("name" . "aflags") ("ver" . "2009,2010,2011,2012,2013,2014,2015,2016"))
                             (("name" . "angbase") ("ver" . "2009,2010,2011,2012,2013,2014,2015,2016"))
                             (("name" . "angdir") ("ver" . "2009,2010,2011,2012,2013,2014,2015,2016"))
                             (("name" . "annoallvisible") ("ver" . "2009,2010,2011,2012,2013,2014,2015,2016"))
                             (("name" . "annoautoscale") ("ver" . "2009,2010,2011,2012,2013,2014,2015,2016"))
                             (("name" . "annomonitor") ("ver" . "2013,2014,2015,2016"))
                             (("name" . "annotativedwg") ("ver" . "2009,2010,2011,2012,2013,2014,2015,2016"))
                             (("name" . "apbox") ("ver" . "2009,2010,2011,2012,2013,2014,2015,2016"))
                             (("name" . "aperture") ("ver" . "2009,2010,2011,2012,2013,2014,2015,2016"))
                             (("name" . "appautoload") ("ver" . "2012,2013,2014,2015,2016"))
                             (("name" . "appframeresources") ("ver" . "2010,2011,2012,2013,2014,2015,2016"))
                             (("name" . "applyglobalopacities") ("ver" . "2011,2012,2013,2014,2015,2016"))
                             (("name" . "area") ("ver" . "2009,2010,2011,2012,2013,2014,2015,2016"))
                             (("name" . "arrayassociativity") ("ver" . "2013,2014,2015,2016"))
                             (("name" . "arraycreation") ("ver" . "2013,2014,2015,2016"))
                             (("name" . "arrayeditstate") ("ver" . "2012,2013,2014,2015,2016"))
                             (("name" . "arraytype") ("ver" . "2012,2013,2014,2015,2016"))
                             (("name" . "assiststate") ("ver" . "2009,2010,2011,2012,2013,2014,2015,2016"))
                             (("name" . "attdia") ("ver" . "2009,2010,2011,2012,2013,2014,2015,2016"))
                             (("name" . "attipe") ("ver" . "2009,2010,2011,2012,2013,2014,2015,2016"))
                             (("name" . "attmode") ("ver" . "2009,2010,2011,2012,2013,2014,2015,2016"))
                             (("name" . "attmulti") ("ver" . "2009,2010,2011,2012,2013,2014,2015,2016"))
                             (("name" . "attreq") ("ver" . "2009,2010,2011,2012,2013,2014,2015,2016"))
                             (("name" . "auditctl") ("ver" . "2009,2010,2011,2012,2013,2014,2015,2016"))
                             (("name" . "aunits") ("ver" . "2009,2010,2011,2012,2013,2014,2015,2016"))
                             (("name" . "auprec") ("ver" . "2009,2010,2011,2012,2013,2014,2015,2016"))
                             (("name" . "autocompletedelay") ("ver" . "2012,2013,2014,2015"))
                             (("name" . "autocompletemode") ("ver" . "2012,2013,2014,2015"))
                             (("name" . "autodwfpublish") ("ver" . "2009,2010,2011,2012,2013,2014,2015,2016"))
                             (("name" . "autoload") ("ver" . "2013"))
                             (("name" . "autoloadpath") ("ver" . "2013"))
                             (("name" . "automaticpub") ("ver" . "2010,2011,2012,2013,2014,2015,2016"))
                             (("name" . "autosnap") ("ver" . "2009,2010,2011,2012,2013,2014,2015,2016"))
                             (("name" . "auxstat") ("ver" . "2009,2010,2011,2012,2013,2014,2015,2016"))
                             (("name" . "axisunit") ("ver" . "2009,2010,2011,2012,2013,2014,2015,2016"))
                             (("name" . "backgroundplot") ("ver" . "2009,2010,2011,2012,2013,2014,2015,2016"))
                             (("name" . "backz") ("ver" . "2009,2010,2011,2012,2013,2014,2015,2016"))
                             (("name" . "bactionbarmode") ("ver" . "2010,2011,2012,2013,2014,2015,2016"))
                             (("name" . "bactioncolor") ("ver" . "2009,2010,2011,2012,2013,2014,2015,2016"))
                             (("name" . "bconstatusmode") ("ver" . "2010,2011,2012,2013,2014,2015,2016"))
                             (("name" . "bdependencyhighlight") ("ver" . "2009,2010,2011,2012,2013,2014,2015,2016"))
                             (("name" . "bgripobjcolor") ("ver" . "2009,2010,2011,2012,2013,2014,2015,2016"))
                             (("name" . "bgripobjsize") ("ver" . "2009,2010,2011,2012,2013,2014,2015,2016"))
                             (("name" . "bindtype") ("ver" . "2009,2010,2011,2012,2013,2014,2015,2016"))
                             (("name" . "blipmode") ("ver" . "2009,2010,2011,2012,2013,2014,2015,2016"))
                             (("name" . "blockeditlock") ("ver" . "2009,2010,2011,2012,2013,2014,2015,2016"))
                             (("name" . "blockeditor") ("ver" . "2009,2010,2011,2012,2013,2014,2015,2016"))
                             (("name" . "blocktestwindow") ("ver" . "2010,2011,2012,2013,2014,2015,2016"))
                             (("name" . "bparametercolor") ("ver" . "2009,2010,2011,2012,2013,2014,2015,2016"))
                             (("name" . "bparameterfont") ("ver" . "2009,2010,2011,2012,2013,2014,2015,2016"))
                             (("name" . "bparametersize") ("ver" . "2009,2010,2011,2012,2013,2014,2015,2016"))
                             (("name" . "bptexthorizontal") ("ver" . "2010,2011,2012,2013,2014,2015,2016"))
                             (("name" . "btmarkdisplay") ("ver" . "2009,2010,2011,2012,2013,2014,2015,2016"))
                             (("name" . "bvmode") ("ver" . "2009,2010,2011,2012,2013,2014,2015,2016"))
                             (("name" . "cachemaxfiles") ("ver" . "2013,2014,2015,2016"))
                             (("name" . "cachemaxtotalsize") ("ver" . "2013,2014,2015,2016"))
                             (("name" . "calcinput") ("ver" . "2009,2010,2011,2012,2013,2014,2015,2016"))
                             (("name" . "cameradisplay") ("ver" . "2009,2010,2011,2012,2013,2014,2015,2016"))
                             (("name" . "cameraheight") ("ver" . "2009,2010,2011,2012,2013,2014,2015,2016"))
                             (("name" . "cannoscale") ("ver" . "2009,2010,2011,2012,2013,2014,2015,2016"))
                             (("name" . "cannoscalevalue") ("ver" . "2009,2010,2011,2012,2013,2014,2015,2016"))
                             (("name" . "capturethumbnails") ("ver" . "2009,2010,2011,2012,2013,2014,2015,2016"))
                             (("name" . "cbardisplaymode") ("ver" . "2009"))
                             (("name" . "cbartransparency") ("ver" . "2010,2011,2012,2013,2014,2015,2016"))
                             (("name" . "cconstraintform") ("ver" . "2010,2011,2012,2013,2014,2015,2016"))
                             (("name" . "cdate") ("ver" . "2009,2010,2011,2012,2013,2014,2015,2016"))
                             (("name" . "cdyndisplaymode") ("ver" . "2009,2010,2011,2012,2013,2014,2015,2016"))
                             (("name" . "cecolor") ("ver" . "2009,2010,2011,2012,2013,2014,2015,2016"))
                             (("name" . "celtscale") ("ver" . "2009,2010,2011,2012,2013,2014,2015,2016"))
                             (("name" . "celtype") ("ver" . "2009,2010,2011,2012,2013,2014,2015,2016"))
                             (("name" . "celweight") ("ver" . "2009,2010,2011,2012,2013,2014,2015,2016"))
                             (("name" . "centermt") ("ver" . "2009,2010,2011,2012,2013,2014,2015,2016"))
                             (("name" . "cetransparency") ("ver" . "2011,2012,2013,2014,2015,2016"))
                             (("name" . "cgeocs") ("ver" . "2014,2015,2016"))
                             (("name" . "chamfera") ("ver" . "2009,2010,2011,2012,2013,2014,2015,2016"))
                             (("name" . "chamferb") ("ver" . "2009,2010,2011,2012,2013,2014,2015,2016"))
                             (("name" . "chamferc") ("ver" . "2009,2010,2011,2012,2013,2014,2015,2016"))
                             (("name" . "chamferd") ("ver" . "2009,2010,2011,2012,2013,2014,2015,2016"))
                             (("name" . "chammode") ("ver" . "2009,2010,2011,2012,2013,2014,2015,2016"))
                             (("name" . "cipmode") ("ver" . "2009,2010,2011,2012,2013,2014,2015,2016"))
                             (("name" . "circlerad") ("ver" . "2009,2010,2011,2012,2013,2014,2015,2016"))
                             (("name" . "classickeys") ("ver" . "2011,2012,2013,2014,2015,2016"))
                             (("name" . "clayer") ("ver" . "2009,2010,2011,2012,2013,2014,2015,2016"))
                             (("name" . "clayout") ("ver" . "2014,2015,2016"))
                             (("name" . "cleanscreenstate") ("ver" . "2009,2010,2011,2012,2013,2014,2015,2016"))
                             (("name" . "clipromptlines") ("ver" . "2013,2014,2015,2016"))
                             (("name" . "clipromptupdate") ("ver" . "2013,2014,2015,2016"))
                             (("name" . "cmaterial") ("ver" . "2009,2010,2011,2012,2013,2014,2015,2016"))
                             (("name" . "cmdactive") ("ver" . "2009,2010,2011,2012,2013,2014,2015,2016"))
                             (("name" . "cmddia") ("ver" . "2009,2010,2011,2012,2013,2014,2015,2016"))
                             (("name" . "cmdecho") ("ver" . "2009,2010,2011,2012,2013,2014,2015,2016"))
                             (("name" . "cmdinputhistorymax") ("ver" . "2009,2010,2011,2012,2013,2014,2015,2016"))
                             (("name" . "cmdnames") ("ver" . "2009,2010,2011,2012,2013,2014,2015,2016"))
                             (("name" . "cmfadecolor") ("ver" . "2016"))
                             (("name" . "cmfadeopacity") ("ver" . "2016"))
                             (("name" . "cmleaderstyle") ("ver" . "2009,2010,2011,2012,2013,2014,2015,2016"))
                             (("name" . "cmljust") ("ver" . "2009,2010,2011,2012,2013,2014,2015,2016"))
                             (("name" . "cmlscale") ("ver" . "2009,2010,2011,2012,2013,2014,2015,2016"))
                             (("name" . "cmlstyle") ("ver" . "2009,2010,2011,2012,2013,2014,2015,2016"))
                             (("name" . "cnameformat") ("ver" . "2009"))
                             (("name" . "colortheme") ("ver" . "2015,2016"))
                             (("name" . "commandpreview") ("ver" . "2015,2016"))
                             (("name" . "compass") ("ver" . "2009,2010,2011,2012,2013,2014,2015,2016"))
                             (("name" . "complexltpreview") ("ver" . "2015,2016"))
                             (("name" . "constraintbardisplay") ("ver" . "2010,2011,2012,2013,2014,2015,2016"))
                             (("name" . "constraintbarmode") ("ver" . "2010,2011,2012,2013,2014,2015,2016"))
                             (("name" . "constraintcursordisplay") ("ver" . "2011,2012,2013,2014,2015,2016"))
                             (("name" . "constraintinfer") ("ver" . "2011,2012,2013,2014,2015,2016"))
                             (("name" . "constraintnameformat") ("ver" . "2010,2011,2012,2013,2014,2015,2016"))
                             (("name" . "constraintrelax") ("ver" . "2009,2010,2011,2012,2013,2014,2015,2016"))
                             (("name" . "constraintsolvemode") ("ver" . "2009,2010,2011,2012,2013,2014,2015,2016"))
                             (("name" . "contentexplorerstate") ("ver" . "2016"))
                             (("name" . "coords") ("ver" . "2009,2010,2011,2012,2013,2014,2015,2016"))
                             (("name" . "copymode") ("ver" . "2009,2010,2011,2012,2013,2014,2015,2016"))
                             (("name" . "cplotstyle") ("ver" . "2009,2010,2011,2012,2013,2014,2015,2016"))
                             (("name" . "cprofile") ("ver" . "2009,2010,2011,2012,2013,2014,2015,2016"))
                             (("name" . "cputicks") ("ver" . "2009,2010,2011,2012,2013,2014,2015,2016"))
                             (("name" . "crossingareacolor") ("ver" . "2009,2010,2011,2012,2013,2014,2015,2016"))
                             (("name" . "cshadow") ("ver" . "2009,2010,2011,2012,2013,2014,2015,2016"))
                             (("name" . "ctab") ("ver" . "2009,2010,2011,2012,2013,2014,2015,2016"))
                             (("name" . "ctablestyle") ("ver" . "2009,2010,2011,2012,2013,2014,2015,2016"))
                             (("name" . "cullingobj") ("ver" . "2011,2012,2013,2014,2015,2016"))
                             (("name" . "cullingobjselection") ("ver" . "2011,2012,2013,2014,2015,2016"))
                             (("name" . "currentprofile") ("ver" . "2009,2010,2011,2012,2013,2014,2015,2016"))
                             (("name" . "cursorbadge") ("ver" . "2015,2016"))
                             (("name" . "cursorsize") ("ver" . "2009,2010,2011,2012,2013,2014,2015,2016"))
                             (("name" . "cviewdetailstyle") ("ver" . "2013,2014,2015,2016"))
                             (("name" . "cviewsectionstyle") ("ver" . "2013,2014,2015,2016"))
                             (("name" . "cvport") ("ver" . "2009,2010,2011,2012,2013,2014,2015,2016"))
                             (("name" . "datalinknotify") ("ver" . "2009,2010,2011,2012,2013,2014,2015,2016"))
                             (("name" . "date") ("ver" . "2009,2010,2011,2012,2013,2014,2015,2016"))
                             (("name" . "dbcstate") ("ver" . "2009,2010,2011,2012,2013,2014,2015,2016"))
                             (("name" . "dblclkedit") ("ver" . "2009,2010,2011,2012,2013,2014,2015,2016"))
                             (("name" . "dbmod") ("ver" . "2009,2010,2011,2012,2013,2014,2015,2016"))
                             (("name" . "dctcust") ("ver" . "2009,2010,2011,2012,2013,2014,2015,2016"))
                             (("name" . "dctmain") ("ver" . "2009,2010,2011,2012,2013,2014,2015,2016"))
                             (("name" . "defaultgizmo") ("ver" . "2010,2011,2012,2013,2014,2015,2016"))
                             (("name" . "defaultindex") ("ver" . "2010,2011,2012,2013,2014,2015,2016"))
                             (("name" . "defaultlighting") ("ver" . "2009,2010,2011,2012,2013,2014,2015,2016"))
                             (("name" . "defaultlightingtype") ("ver" . "2009,2010,2011,2012,2013,2014,2015,2016"))
                             (("name" . "deflplstyle") ("ver" . "2009,2010,2011,2012,2013,2014,2015,2016"))
                             (("name" . "defplstyle") ("ver" . "2009,2010,2011,2012,2013,2014,2015,2016"))
                             (("name" . "delobj") ("ver" . "2009,2010,2011,2012,2013,2014,2015,2016"))
                             (("name" . "demandload") ("ver" . "2009,2010,2011,2012,2013,2014,2015,2016"))
                             (("name" . "designfeedstate") ("ver" . "2014,2015,2016"))
                             (("name" . "dgnframe") ("ver" . "2009,2010,2011,2012,2013,2014,2015,2016"))
                             (("name" . "dgnimportmax") ("ver" . "2009,2010,2011,2012,2013,2014,2015,2016"))
                             (("name" . "dgnimportmode") ("ver" . "2012,2013,2014,2015,2016"))
                             (("name" . "dgnimportunitconversion") ("ver" . "2012,2013,2014,2015,2016"))
                             (("name" . "dgnmappingpath") ("ver" . "2009,2010,2011,2012,2013,2014,2015,2016"))
                             (("name" . "dgnosnap") ("ver" . "2009,2010,2011,2012,2013,2014,2015,2016"))
                             (("name" . "diastat") ("ver" . "2009,2010,2011,2012,2013,2014,2015,2016"))
                             (("name" . "digitizer") ("ver" . "2011,2012,2013,2014,2015,2016"))
                             (("name" . "dimadec") ("ver" . "2009,2010,2011,2012,2013,2014,2015,2016"))
                             (("name" . "dimalt") ("ver" . "2009,2010,2011,2012,2013,2014,2015,2016"))
                             (("name" . "dimaltd") ("ver" . "2009,2010,2011,2012,2013,2014,2015,2016"))
                             (("name" . "dimaltf") ("ver" . "2009,2010,2011,2012,2013,2014,2015,2016"))
                             (("name" . "dimaltrnd") ("ver" . "2009,2010,2011,2012,2013,2014,2015,2016"))
                             (("name" . "dimalttd") ("ver" . "2009,2010,2011,2012,2013,2014,2015,2016"))
                             (("name" . "dimalttz") ("ver" . "2009,2010,2011,2012,2013,2014,2015,2016"))
                             (("name" . "dimaltu") ("ver" . "2009,2010,2011,2012,2013,2014,2015,2016"))
                             (("name" . "dimaltz") ("ver" . "2009,2010,2011,2012,2013,2014,2015,2016"))
                             (("name" . "dimanno") ("ver" . "2009,2010,2011,2012,2013,2014,2015,2016"))
                             (("name" . "dimapost") ("ver" . "2009,2010,2011,2012,2013,2014,2015,2016"))
                             (("name" . "dimarcsym") ("ver" . "2009,2010,2011,2012,2013,2014,2015,2016"))
                             (("name" . "dimaso") ("ver" . "2009,2010,2011,2012,2013,2014,2015,2016"))
                             (("name" . "dimassoc") ("ver" . "2009,2010,2011,2012,2013,2014,2015,2016"))
                             (("name" . "dimasz") ("ver" . "2009,2010,2011,2012,2013,2014,2015,2016"))
                             (("name" . "dimatfit") ("ver" . "2009,2010,2011,2012,2013,2014,2015,2016"))
                             (("name" . "dimaunit") ("ver" . "2009,2010,2011,2012,2013,2014,2015,2016"))
                             (("name" . "dimazin") ("ver" . "2009,2010,2011,2012,2013,2014,2015,2016"))
                             (("name" . "dimblk") ("ver" . "2009,2010,2011,2012,2013,2014,2015,2016"))
                             (("name" . "dimblk1") ("ver" . "2009,2010,2011,2012,2013,2014,2015,2016"))
                             (("name" . "dimblk2") ("ver" . "2009,2010,2011,2012,2013,2014,2015,2016"))
                             (("name" . "dimcen") ("ver" . "2009,2010,2011,2012,2013,2014,2015,2016"))
                             (("name" . "dimclrd") ("ver" . "2009,2010,2011,2012,2013,2014,2015,2016"))
                             (("name" . "dimclre") ("ver" . "2009,2010,2011,2012,2013,2014,2015,2016"))
                             (("name" . "dimclrt") ("ver" . "2009,2010,2011,2012,2013,2014,2015,2016"))
                             (("name" . "dimconstrainticon") ("ver" . "2010,2011,2012,2013,2014,2015,2016"))
                             (("name" . "dimcontinuemode") ("ver" . "2014,2015,2016"))
                             (("name" . "dimdec") ("ver" . "2009,2010,2011,2012,2013,2014,2015,2016"))
                             (("name" . "dimdle") ("ver" . "2009,2010,2011,2012,2013,2014,2015,2016"))
                             (("name" . "dimdli") ("ver" . "2009,2010,2011,2012,2013,2014,2015,2016"))
                             (("name" . "dimdsep") ("ver" . "2009,2010,2011,2012,2013,2014,2015,2016"))
                             (("name" . "dimexe") ("ver" . "2009,2010,2011,2012,2013,2014,2015,2016"))
                             (("name" . "dimexo") ("ver" . "2009,2010,2011,2012,2013,2014,2015,2016"))
                             (("name" . "dimfit") ("ver" . "2009,2010,2011,2012,2013,2014,2015,2016"))
                             (("name" . "dimfrac") ("ver" . "2009,2010,2011,2012,2013,2014,2015,2016"))
                             (("name" . "dimfxl") ("ver" . "2009,2010,2011,2012,2013,2014,2015,2016"))
                             (("name" . "dimfxlon") ("ver" . "2009,2010,2011,2012,2013,2014,2015,2016"))
                             (("name" . "dimgap") ("ver" . "2009,2010,2011,2012,2013,2014,2015,2016"))
                             (("name" . "dimjogang") ("ver" . "2009,2010,2011,2012,2013,2014,2015,2016"))
                             (("name" . "dimjust") ("ver" . "2009,2010,2011,2012,2013,2014,2015,2016"))
                             (("name" . "dimlayer") ("ver" . "2016"))
                             (("name" . "dimldrblk") ("ver" . "2009,2010,2011,2012,2013,2014,2015,2016"))
                             (("name" . "dimlfac") ("ver" . "2009,2010,2011,2012,2013,2014,2015,2016"))
                             (("name" . "dimlim") ("ver" . "2009,2010,2011,2012,2013,2014,2015,2016"))
                             (("name" . "dimltex1") ("ver" . "2009,2010,2011,2012,2013,2014,2015,2016"))
                             (("name" . "dimltex2") ("ver" . "2009,2010,2011,2012,2013,2014,2015,2016"))
                             (("name" . "dimltype") ("ver" . "2009,2010,2011,2012,2013,2014,2015,2016"))
                             (("name" . "dimlunit") ("ver" . "2009,2010,2011,2012,2013,2014,2015,2016"))
                             (("name" . "dimlwd") ("ver" . "2009,2010,2011,2012,2013,2014,2015,2016"))
                             (("name" . "dimlwe") ("ver" . "2009,2010,2011,2012,2013,2014,2015,2016"))
                             (("name" . "dimpickbox") ("ver" . "2016"))
                             (("name" . "dimpost") ("ver" . "2009,2010,2011,2012,2013,2014,2015,2016"))
                             (("name" . "dimrnd") ("ver" . "2009,2010,2011,2012,2013,2014,2015,2016"))
                             (("name" . "dimsah") ("ver" . "2009,2010,2011,2012,2013,2014,2015,2016"))
                             (("name" . "dimscale") ("ver" . "2009,2010,2011,2012,2013,2014,2015,2016"))
                             (("name" . "dimsd1") ("ver" . "2009,2010,2011,2012,2013,2014,2015,2016"))
                             (("name" . "dimsd2") ("ver" . "2009,2010,2011,2012,2013,2014,2015,2016"))
                             (("name" . "dimse1") ("ver" . "2009,2010,2011,2012,2013,2014,2015,2016"))
                             (("name" . "dimse2") ("ver" . "2009,2010,2011,2012,2013,2014,2015,2016"))
                             (("name" . "dimsho") ("ver" . "2009,2010,2011,2012,2013,2014,2015,2016"))
                             (("name" . "dimsoxd") ("ver" . "2009,2010,2011,2012,2013,2014,2015,2016"))
                             (("name" . "dimstyle") ("ver" . "2009,2010,2011,2012,2013,2014,2015,2016"))
                             (("name" . "dimtad") ("ver" . "2009,2010,2011,2012,2013,2014,2015,2016"))
                             (("name" . "dimtdec") ("ver" . "2009,2010,2011,2012,2013,2014,2015,2016"))
                             (("name" . "dimtfac") ("ver" . "2009,2010,2011,2012,2013,2014,2015,2016"))
                             (("name" . "dimtfill") ("ver" . "2009,2010,2011,2012,2013,2014,2015,2016"))
                             (("name" . "dimtfillclr") ("ver" . "2009,2010,2011,2012,2013,2014,2015,2016"))
                             (("name" . "dimtih") ("ver" . "2009,2010,2011,2012,2013,2014,2015,2016"))
                             (("name" . "dimtix") ("ver" . "2009,2010,2011,2012,2013,2014,2015,2016"))
                             (("name" . "dimtm") ("ver" . "2009,2010,2011,2012,2013,2014,2015,2016"))
                             (("name" . "dimtmove") ("ver" . "2009,2010,2011,2012,2013,2014,2015,2016"))
                             (("name" . "dimtofl") ("ver" . "2009,2010,2011,2012,2013,2014,2015,2016"))
                             (("name" . "dimtoh") ("ver" . "2009,2010,2011,2012,2013,2014,2015,2016"))
                             (("name" . "dimtol") ("ver" . "2009,2010,2011,2012,2013,2014,2015,2016"))
                             (("name" . "dimtolj") ("ver" . "2009,2010,2011,2012,2013,2014,2015,2016"))
                             (("name" . "dimtp") ("ver" . "2009,2010,2011,2012,2013,2014,2015,2016"))
                             (("name" . "dimtsz") ("ver" . "2009,2010,2011,2012,2013,2014,2015,2016"))
                             (("name" . "dimtvp") ("ver" . "2009,2010,2011,2012,2013,2014,2015,2016"))
                             (("name" . "dimtxsty") ("ver" . "2009,2010,2011,2012,2013,2014,2015,2016"))
                             (("name" . "dimtxt") ("ver" . "2009,2010,2011,2012,2013,2014,2015,2016"))
                             (("name" . "dimtxtdirection") ("ver" . "2010,2011,2012,2013,2014,2015,2016"))
                             (("name" . "dimtxtruler") ("ver" . "2016"))
                             (("name" . "dimtzin") ("ver" . "2009,2010,2011,2012,2013,2014,2015,2016"))
                             (("name" . "dimunit") ("ver" . "2009,2010,2011,2012,2013,2014,2015,2016"))
                             (("name" . "dimupt") ("ver" . "2009,2010,2011,2012,2013,2014,2015,2016"))
                             (("name" . "dimzin") ("ver" . "2009,2010,2011,2012,2013,2014,2015,2016"))
                             (("name" . "displayviewcubein2d") ("ver" . "2013,2014,2015,2016"))
                             (("name" . "displayviewcubein3d") ("ver" . "2015,2016"))
                             (("name" . "dispsilh") ("ver" . "2009,2010,2011,2012,2013,2014,2015,2016"))
                             (("name" . "distance") ("ver" . "2009,2010,2011,2012,2013,2014,2015,2016"))
                             (("name" . "divmeshboxheight") ("ver" . "2010,2011,2012,2013,2014,2015,2016"))
                             (("name" . "divmeshboxlength") ("ver" . "2010,2011,2012,2013,2014,2015,2016"))
                             (("name" . "divmeshboxwidth") ("ver" . "2010,2011,2012,2013,2014,2015,2016"))
                             (("name" . "divmeshconeaxis") ("ver" . "2010,2011,2012,2013,2014,2015,2016"))
                             (("name" . "divmeshconebase") ("ver" . "2010,2011,2012,2013,2014,2015,2016"))
                             (("name" . "divmeshconeheight") ("ver" . "2010,2011,2012,2013,2014,2015,2016"))
                             (("name" . "divmeshcylaxis") ("ver" . "2010,2011,2012,2013,2014,2015,2016"))
                             (("name" . "divmeshcylbase") ("ver" . "2010,2011,2012,2013,2014,2015,2016"))
                             (("name" . "divmeshcylheight") ("ver" . "2010,2011,2012,2013,2014,2015,2016"))
                             (("name" . "divmeshpyrbase") ("ver" . "2010,2011,2012,2013,2014,2015,2016"))
                             (("name" . "divmeshpyrheight") ("ver" . "2010,2011,2012,2013,2014,2015,2016"))
                             (("name" . "divmeshpyrlength") ("ver" . "2010,2011,2012,2013,2014,2015,2016"))
                             (("name" . "divmeshsphereaxis") ("ver" . "2010,2011,2012,2013,2014,2015,2016"))
                             (("name" . "divmeshsphereheight") ("ver" . "2010,2011,2012,2013,2014,2015,2016"))
                             (("name" . "divmeshtoruspath") ("ver" . "2010,2011,2012,2013,2014,2015,2016"))
                             (("name" . "divmeshtorussection") ("ver" . "2010,2011,2012,2013,2014,2015,2016"))
                             (("name" . "divmeshwedgebase") ("ver" . "2010,2011,2012,2013,2014,2015,2016"))
                             (("name" . "divmeshwedgeheight") ("ver" . "2010,2011,2012,2013,2014,2015,2016"))
                             (("name" . "divmeshwedgelength") ("ver" . "2010,2011,2012,2013,2014,2015,2016"))
                             (("name" . "divmeshwedgeslope") ("ver" . "2010,2011,2012,2013,2014,2015,2016"))
                             (("name" . "divmeshwedgewidth") ("ver" . "2010,2011,2012,2013,2014,2015,2016"))
                             (("name" . "donutid") ("ver" . "2009,2010,2011,2012,2013,2014,2015,2016"))
                             (("name" . "donutod") ("ver" . "2009,2010,2011,2012,2013,2014,2015,2016"))
                             (("name" . "dragmode") ("ver" . "2009,2010,2011,2012,2013,2014,2015,2016"))
                             (("name" . "dragp1") ("ver" . "2009,2010,2011,2012,2013,2014,2015,2016"))
                             (("name" . "dragp2") ("ver" . "2009,2010,2011,2012,2013,2014,2015,2016"))
                             (("name" . "dragvs") ("ver" . "2009,2010,2011,2012,2013,2014,2015,2016"))
                             (("name" . "draworderctl") ("ver" . "2009,2010,2011,2012,2013,2014,2015,2016"))
                             (("name" . "drstate") ("ver" . "2009,2010,2011,2012,2013,2014,2015,2016"))
                             (("name" . "dtexted") ("ver" . "2009,2010,2011,2012,2013,2014,2015,2016"))
                             (("name" . "dwfframe") ("ver" . "2009,2010,2011,2012,2013,2014,2015,2016"))
                             (("name" . "dwfosnap") ("ver" . "2009,2010,2011,2012,2013,2014,2015,2016"))
                             (("name" . "dwgcheck") ("ver" . "2009,2010,2011,2012,2013,2014,2015,2016"))
                             (("name" . "dwgcodepage") ("ver" . "2009,2010,2011,2012,2013,2014,2015,2016"))
                             (("name" . "dwgname") ("ver" . "2009,2010,2011,2012,2013,2014,2015,2016"))
                             (("name" . "dwgprefix") ("ver" . "2009,2010,2011,2012,2013,2014,2015,2016"))
                             (("name" . "dwgtitled") ("ver" . "2009,2010,2011,2012,2013,2014,2015,2016"))
                             (("name" . "dxeval") ("ver" . "2009,2010,2011,2012,2013,2014,2015,2016"))
                             (("name" . "dynconstraintdisplay") ("ver" . "2010,2011,2012,2013,2014,2015,2016"))
                             (("name" . "dynconstraintmode") ("ver" . "2010,2011,2012,2013,2014,2015,2016"))
                             (("name" . "dyndigrip") ("ver" . "2009,2010,2011,2012,2013,2014,2015,2016"))
                             (("name" . "dyndivis") ("ver" . "2009,2010,2011,2012,2013,2014,2015,2016"))
                             (("name" . "dyninfotips") ("ver" . "2012,2013,2014,2015,2016"))
                             (("name" . "dynmode") ("ver" . "2009,2010,2011,2012,2013,2014,2015,2016"))
                             (("name" . "dynpicoords") ("ver" . "2009,2010,2011,2012,2013,2014,2015,2016"))
                             (("name" . "dynpiformat") ("ver" . "2009,2010,2011,2012,2013,2014,2015,2016"))
                             (("name" . "dynpivis") ("ver" . "2009,2010,2011,2012,2013,2014,2015,2016"))
                             (("name" . "dynprompt") ("ver" . "2009,2010,2011,2012,2013,2014,2015,2016"))
                             (("name" . "dyntooltips") ("ver" . "2009,2010,2011,2012,2013,2014,2015,2016"))
                             (("name" . "edgemode") ("ver" . "2009,2010,2011,2012,2013,2014,2015,2016"))
                             (("name" . "elevation") ("ver" . "2009,2010,2011,2012,2013,2014,2015,2016"))
                             (("name" . "enterprisemenu") ("ver" . "2009,2010,2011,2012,2013,2014,2015,2016"))
                             (("name" . "erhighlight") ("ver" . "2011,2012,2013,2014,2015,2016"))
                             (("name" . "errno") ("ver" . "2009,2010,2011,2012,2013,2014,2015,2016"))
                             (("name" . "expert") ("ver" . "2009,2010,2011,2012,2013,2014,2015,2016"))
                             (("name" . "explmode") ("ver" . "2009,2010,2011,2012,2013,2014,2015,2016"))
                             (("name" . "exporteplotformat") ("ver" . "2010,2011,2012,2013,2014,2015,2016"))
                             (("name" . "exportmodelspace") ("ver" . "2010,2011,2012,2013,2014,2015,2016"))
                             (("name" . "exportpagesetup") ("ver" . "2010,2011,2012,2013,2014,2015,2016"))
                             (("name" . "exportpaperspace") ("ver" . "2010,2011,2012,2013,2014,2015,2016"))
                             (("name" . "expvalue") ("ver" . "2016"))
                             (("name" . "expwhitebalance") ("ver" . "2016"))
                             (("name" . "extmax") ("ver" . "2009,2010,2011,2012,2013,2014,2015,2016"))
                             (("name" . "extmin") ("ver" . "2009,2010,2011,2012,2013,2014,2015,2016"))
                             (("name" . "extnames") ("ver" . "2009,2010,2011,2012,2013,2014,2015,2016"))
                             (("name" . "faceterdevnormal") ("ver" . "2010,2011,2012,2013,2014,2015,2016"))
                             (("name" . "faceterdevsurface") ("ver" . "2010,2011,2012,2013,2014,2015,2016"))
                             (("name" . "facetergridratio") ("ver" . "2010,2011,2012,2013,2014,2015,2016"))
                             (("name" . "facetermaxedgelength") ("ver" . "2010,2011,2012,2013,2014,2015,2016"))
                             (("name" . "facetermaxgrid") ("ver" . "2010,2011,2012,2013,2014,2015,2016"))
                             (("name" . "facetermeshtype") ("ver" . "2010,2011,2012,2013,2014,2015,2016"))
                             (("name" . "faceterminugrid") ("ver" . "2010,2011,2012,2013,2014,2015,2016"))
                             (("name" . "faceterminvgrid") ("ver" . "2010,2011,2012,2013,2014,2015,2016"))
                             (("name" . "faceterprimitivemode") ("ver" . "2010,2011,2012,2013,2014,2015,2016"))
                             (("name" . "facetersmoothlev") ("ver" . "2010,2011,2012,2013,2014,2015,2016"))
                             (("name" . "facetratio") ("ver" . "2009,2010,2011,2012,2013,2014,2015,2016"))
                             (("name" . "facetres") ("ver" . "2009,2010,2011,2012,2013,2014,2015,2016"))
                             (("name" . "fbximportlog") ("ver" . "2011,2012,2013,2014,2015,2016"))
                             (("name" . "fiberworld") ("ver" . "2015"))
                             (("name" . "fielddisplay") ("ver" . "2009,2010,2011,2012,2013,2014,2015,2016"))
                             (("name" . "fieldeval") ("ver" . "2009,2010,2011,2012,2013,2014,2015,2016"))
                             (("name" . "filedia") ("ver" . "2009,2010,2011,2012,2013,2014,2015,2016"))
                             (("name" . "filetabpreview") ("ver" . "2014,2015,2016"))
                             (("name" . "filetabstate") ("ver" . "2014,2015,2016"))
                             (("name" . "filetabthumbhover") ("ver" . "2014,2015,2016"))
                             (("name" . "filletrad") ("ver" . "2009,2010,2011,2012,2013,2014,2015,2016"))
                             (("name" . "filletrad3d") ("ver" . "2011,2012,2013,2014,2015,2016"))
                             (("name" . "fillmode") ("ver" . "2009,2010,2011,2012,2013,2014,2015,2016"))
                             (("name" . "fontalt") ("ver" . "2009,2010,2011,2012,2013,2014,2015,2016"))
                             (("name" . "fontmap") ("ver" . "2009,2010,2011,2012,2013,2014,2015,2016"))
                             (("name" . "frame") ("ver" . "2010,2011,2012,2013,2014,2015,2016"))
                             (("name" . "frameselection") ("ver" . "2012,2013,2014,2015,2016"))
                             (("name" . "frontz") ("ver" . "2009,2010,2011,2012,2013,2014,2015,2016"))
                             (("name" . "fullopen") ("ver" . "2009,2010,2011,2012,2013,2014,2015,2016"))
                             (("name" . "fullplotpath") ("ver" . "2009,2010,2011,2012,2013,2014,2015,2016"))
                             (("name" . "galleryview") ("ver" . "2016"))
                             (("name" . "geolatlongformat") ("ver" . "2009,2010,2011,2012,2013,2014,2015,2016"))
                             (("name" . "geolocatemode") ("ver" . "2014,2015,2016"))
                             (("name" . "geomapmode") ("ver" . "2014,2015,2016"))
                             (("name" . "geomarkervisibility") ("ver" . "2009,2010,2011,2012,2013,2014,2015,2016"))
                             (("name" . "geomarkpositionsize") ("ver" . "2014,2015,2016"))
                             (("name" . "gfang") ("ver" . "2009,2010,2011,2012,2013,2014,2015,2016"))
                             (("name" . "gfclr1") ("ver" . "2009,2010,2011,2012,2013,2014,2015,2016"))
                             (("name" . "gfclr2") ("ver" . "2009,2010,2011,2012,2013,2014,2015,2016"))
                             (("name" . "gfclrlum") ("ver" . "2009,2010,2011,2012,2013,2014,2015,2016"))
                             (("name" . "gfclrstate") ("ver" . "2009,2010,2011,2012,2013,2014,2015,2016"))
                             (("name" . "gfname") ("ver" . "2009,2010,2011,2012,2013,2014,2015,2016"))
                             (("name" . "gfshift") ("ver" . "2009,2010,2011,2012,2013,2014,2015,2016"))
                             (("name" . "globalopacity") ("ver" . "2011,2012,2013,2014,2015,2016"))
                             (("name" . "griddisplay") ("ver" . "2009,2010,2011,2012,2013,2014,2015,2016"))
                             (("name" . "gridmajor") ("ver" . "2009,2010,2011,2012,2013,2014,2015,2016"))
                             (("name" . "gridmode") ("ver" . "2009,2010,2011,2012,2013,2014,2015,2016"))
                             (("name" . "gridstyle") ("ver" . "2011,2012,2013,2014,2015,2016"))
                             (("name" . "gridunit") ("ver" . "2009,2010,2011,2012,2013,2014,2015,2016"))
                             (("name" . "gripblock") ("ver" . "2009,2010,2011,2012,2013,2014,2015,2016"))
                             (("name" . "gripcolor") ("ver" . "2009,2010,2011,2012,2013,2014,2015,2016"))
                             (("name" . "gripcontour") ("ver" . "2011,2012,2013,2014,2015,2016"))
                             (("name" . "gripdyncolor") ("ver" . "2009,2010,2011,2012,2013,2014,2015,2016"))
                             (("name" . "griphot") ("ver" . "2009,2010,2011,2012,2013,2014,2015,2016"))
                             (("name" . "griphover") ("ver" . "2009,2010,2011,2012,2013,2014,2015,2016"))
                             (("name" . "gripmultifunctional") ("ver" . "2011,2012,2013,2014,2015,2016"))
                             (("name" . "gripobjlimit") ("ver" . "2009,2010,2011,2012,2013,2014,2015,2016"))
                             (("name" . "grips") ("ver" . "2009,2010,2011,2012,2013,2014,2015,2016"))
                             (("name" . "gripsize") ("ver" . "2009,2010,2011,2012,2013,2014,2015,2016"))
                             (("name" . "gripsubobjmode") ("ver" . "2010,2011,2012,2013,2014,2015,2016"))
                             (("name" . "griptips") ("ver" . "2009,2010,2011,2012,2013,2014,2015,2016"))
                             (("name" . "groupdisplaymode") ("ver" . "2012,2013,2014,2015,2016"))
                             (("name" . "gtauto") ("ver" . "2009,2010,2011,2012,2013,2014,2015,2016"))
                             (("name" . "gtdefault") ("ver" . "2009,2010,2011,2012,2013,2014,2015,2016"))
                             (("name" . "gtlocation") ("ver" . "2009,2010,2011,2012,2013,2014,2015,2016"))
                             (("name" . "halogap") ("ver" . "2009,2010,2011,2012,2013,2014,2015,2016"))
                             (("name" . "handles") ("ver" . "2009,2010,2011,2012,2013,2014,2015,2016"))
                             (("name" . "hatchboundset") ("ver" . "2011,2012,2013,2014,2015,2016"))
                             (("name" . "hatchcreation") ("ver" . "2011,2012,2013,2014,2015,2016"))
                             (("name" . "hatchtype") ("ver" . "2011,2012,2013,2014,2015,2016"))
                             (("name" . "helpprefix") ("ver" . "2011,2012,2013,2014,2015,2016"))
                             (("name" . "hideprecision") ("ver" . "2009,2010,2011,2012,2013,2014,2015,2016"))
                             (("name" . "hidetext") ("ver" . "2009,2010,2011,2012,2013,2014,2015,2016"))
                             (("name" . "hidexrefscales") ("ver" . "2009,2010,2011,2012,2013,2014,2015,2016"))
                             (("name" . "highlight") ("ver" . "2009,2010,2011,2012,2013,2014,2015,2016"))
                             (("name" . "highlightsmoothing") ("ver" . "2015,2016"))
                             (("name" . "hpang") ("ver" . "2009,2010,2011,2012,2013,2014,2015,2016"))
                             (("name" . "hpannotative") ("ver" . "2011,2012,2013,2014,2015,2016"))
                             (("name" . "hpassoc") ("ver" . "2009,2010,2011,2012,2013,2014,2015,2016"))
                             (("name" . "hpbackgroundcolor") ("ver" . "2011,2012,2013,2014,2015,2016"))
                             (("name" . "hpbound") ("ver" . "2009,2010,2011,2012,2013,2014,2015,2016"))
                             (("name" . "hpboundretain") ("ver" . "2011,2012,2013,2014,2015,2016"))
                             (("name" . "hpcolor") ("ver" . "2011,2012,2013,2014,2015,2016"))
                             (("name" . "hpdlgmode") ("ver" . "2011,2012,2013,2014,2015,2016"))
                             (("name" . "hpdouble") ("ver" . "2009,2010,2011,2012,2013,2014,2015,2016"))
                             (("name" . "hpdraworder") ("ver" . "2009,2010,2011,2012,2013,2014,2015,2016"))
                             (("name" . "hpgaptol") ("ver" . "2009,2010,2011,2012,2013,2014,2015,2016"))
                             (("name" . "hpinherit") ("ver" . "2009,2010,2011,2012,2013,2014,2015,2016"))
                             (("name" . "hpislanddetection") ("ver" . "2011,2012,2013,2014,2015,2016"))
                             (("name" . "hpislanddetectionmode") ("ver" . "2011,2012,2013,2014,2015,2016"))
                             (("name" . "hplastpattern") ("ver" . "2011,2012,2013,2014,2015,2016"))
                             (("name" . "hplayer") ("ver" . "2011,2012,2013,2014,2015,2016"))
                             (("name" . "hplinetype") ("ver" . "2015,2016"))
                             (("name" . "hpmaxareas") ("ver" . "2012,2013,2014,2015,2016"))
                             (("name" . "hpmaxlines") ("ver" . "2009,2010,2011,2012,2013,2014,2015,2016"))
                             (("name" . "hpname") ("ver" . "2009,2010,2011,2012,2013,2014,2015,2016"))
                             (("name" . "hpobjwarning") ("ver" . "2009,2010,2011,2012,2013,2014,2015,2016"))
                             (("name" . "hporigin") ("ver" . "2009,2010,2011,2012,2013,2014,2015,2016"))
                             (("name" . "hporiginmode") ("ver" . "2009,2010,2011,2012,2013,2014,2015,2016"))
                             (("name" . "hporiginstoreasdefault") ("ver" . "2011,2012,2013,2014,2015,2016"))
                             (("name" . "hppickmode") ("ver" . "2014,2015,2016"))
                             (("name" . "hpquickpreview") ("ver" . "2011,2012,2013,2014,2015,2016"))
                             (("name" . "hpquickprevtimeout") ("ver" . "2012,2013,2014,2015,2016"))
                             (("name" . "hprelativeps") ("ver" . "2011,2012,2013,2014,2015,2016"))
                             (("name" . "hpscale") ("ver" . "2009,2010,2011,2012,2013,2014,2015,2016"))
                             (("name" . "hpseparate") ("ver" . "2009,2010,2011,2012,2013,2014,2015,2016"))
                             (("name" . "hpspace") ("ver" . "2009,2010,2011,2012,2013,2014,2015,2016"))
                             (("name" . "hptransparency") ("ver" . "2011,2012,2013,2014,2015,2016"))
                             (("name" . "hyperlinkbase") ("ver" . "2009,2010,2011,2012,2013,2014,2015,2016"))
                             (("name" . "iblenvironment") ("ver" . "2016"))
                             (("name" . "imageframe") ("ver" . "2010,2011,2012,2013,2014,2015,2016"))
                             (("name" . "imagehlt") ("ver" . "2009,2010,2011,2012,2013,2014,2015,2016"))
                             (("name" . "impliedface") ("ver" . "2009,2010,2011,2012,2013,2014,2015,2016"))
                             (("name" . "indexctl") ("ver" . "2009,2010,2011,2012,2013,2014,2015,2016"))
                             (("name" . "inetlocation") ("ver" . "2009,2010,2011,2012,2013,2014,2015,2016"))
                             (("name" . "inputhistorymode") ("ver" . "2009,2010,2011,2012,2013,2014,2015,2016"))
                             (("name" . "inputsearchdelay") ("ver" . "2014,2015,2016"))
                             (("name" . "insbase") ("ver" . "2009,2010,2011,2012,2013,2014,2015,2016"))
                             (("name" . "insname") ("ver" . "2009,2010,2011,2012,2013,2014,2015,2016"))
                             (("name" . "insunits") ("ver" . "2009,2010,2011,2012,2013,2014,2015,2016"))
                             (("name" . "insunitsdefsource") ("ver" . "2009,2010,2011,2012,2013,2014,2015,2016"))
                             (("name" . "insunitsdeftarget") ("ver" . "2009,2010,2011,2012,2013,2014,2015,2016"))
                             (("name" . "intelligentupdate") ("ver" . "2009,2010,2011,2012,2013,2014,2015,2016"))
                             (("name" . "interferecolor") ("ver" . "2009,2010,2011,2012,2013,2014,2015,2016"))
                             (("name" . "interfereobjvs") ("ver" . "2009,2010,2011,2012,2013,2014,2015,2016"))
                             (("name" . "interferevpvs") ("ver" . "2009,2010,2011,2012,2013,2014,2015,2016"))
                             (("name" . "intersectioncolor") ("ver" . "2009,2010,2011,2012,2013,2014,2015,2016"))
                             (("name" . "intersectiondisplay") ("ver" . "2009,2010,2011,2012,2013,2014,2015,2016"))
                             (("name" . "isavebak") ("ver" . "2009,2010,2011,2012,2013,2014,2015,2016"))
                             (("name" . "isavepercent") ("ver" . "2009,2010,2011,2012,2013,2014,2015,2016"))
                             (("name" . "isolines") ("ver" . "2009,2010,2011,2012,2013,2014,2015,2016"))
                             (("name" . "largeobjectsupport") ("ver" . "2010,2011,2012,2013,2014,2015,2016"))
                             (("name" . "lastangle") ("ver" . "2009,2010,2011,2012,2013,2014,2015,2016"))
                             (("name" . "lastpoint") ("ver" . "2009,2010,2011,2012,2013,2014,2015,2016"))
                             (("name" . "lastprompt") ("ver" . "2009,2010,2011,2012,2013,2014,2015,2016"))
                             (("name" . "latitude") ("ver" . "2009,2010,2011,2012,2013,2014,2015,2016"))
                             (("name" . "layerdlgmode") ("ver" . "2009,2010,2011,2012,2013,2014,2015,2016"))
                             (("name" . "layereval") ("ver" . "2009,2010,2011,2012,2013,2014,2015,2016"))
                             (("name" . "layerevalctl") ("ver" . "2009,2010,2011,2012,2013,2014,2015,2016"))
                             (("name" . "layerfilteralert") ("ver" . "2009,2010,2011,2012,2013,2014,2015,2016"))
                             (("name" . "layernotify") ("ver" . "2009,2010,2011,2012,2013,2014,2015,2016"))
                             (("name" . "laylockfadectl") ("ver" . "2009,2010,2011,2012,2013,2014,2015,2016"))
                             (("name" . "layoutcreateviewport") ("ver" . "2012,2013,2014,2015,2016"))
                             (("name" . "layoutregenctl") ("ver" . "2009,2010,2011,2012,2013,2014,2015,2016"))
                             (("name" . "layouttab") ("ver" . "2015,2016"))
                             (("name" . "lazyload") ("ver" . "2009,2010,2011,2012,2013,2014,2015,2016"))
                             (("name" . "legacycodesearch") ("ver" . "2016"))
                             (("name" . "legacyctrlpick") ("ver" . "2009,2010,2011,2012,2013,2014,2015,2016"))
                             (("name" . "lenslength") ("ver" . "2009,2010,2011,2012,2013,2014,2015,2016"))
                             (("name" . "lightglyphdisplay") ("ver" . "2009,2010,2011,2012,2013,2014,2015,2016"))
                             (("name" . "lightingunits") ("ver" . "2009,2010,2011,2012,2013,2014,2015,2016"))
                             (("name" . "lightsinblocks") ("ver" . "2009,2010,2011,2012,2013,2014,2015,2016"))
                             (("name" . "limcheck") ("ver" . "2009,2010,2011,2012,2013,2014,2015,2016"))
                             (("name" . "limmax") ("ver" . "2009,2010,2011,2012,2013,2014,2015,2016"))
                             (("name" . "limmin") ("ver" . "2009,2010,2011,2012,2013,2014,2015,2016"))
                             (("name" . "linearbrightness") ("ver" . "2009,2010,2011,2012,2013,2014,2015,2016"))
                             (("name" . "linearcontrast") ("ver" . "2009,2010,2011,2012,2013,2014,2015,2016"))
                             (("name" . "linefading") ("ver" . "2015,2016"))
                             (("name" . "linefadinglevel") ("ver" . "2016"))
                             (("name" . "linesmoothing") ("ver" . "2015,2016"))
                             (("name" . "lispenabled") ("ver" . "2013"))
                             (("name" . "lispinit") ("ver" . "2009,2010,2011,2012,2013,2014,2015,2016"))
                             (("name" . "locale") ("ver" . "2009,2010,2011,2012,2013,2014,2015,2016"))
                             (("name" . "localrootprefix") ("ver" . "2009,2010,2011,2012,2013,2014,2015,2016"))
                             (("name" . "lockui") ("ver" . "2009,2010,2011,2012,2013,2014,2015,2016"))
                             (("name" . "loftang1") ("ver" . "2009,2010,2011,2012,2013,2014,2015,2016"))
                             (("name" . "loftang2") ("ver" . "2009,2010,2011,2012,2013,2014,2015,2016"))
                             (("name" . "loftmag1") ("ver" . "2009,2010,2011,2012,2013,2014,2015,2016"))
                             (("name" . "loftmag2") ("ver" . "2009,2010,2011,2012,2013,2014,2015,2016"))
                             (("name" . "loftnormals") ("ver" . "2009,2010,2011,2012,2013,2014,2015,2016"))
                             (("name" . "loftparam") ("ver" . "2009,2010,2011,2012,2013,2014,2015,2016"))
                             (("name" . "logexpbrightness") ("ver" . "2009,2010,2011,2012,2013,2014,2015,2016"))
                             (("name" . "logexpcontrast") ("ver" . "2009,2010,2011,2012,2013,2014,2015,2016"))
                             (("name" . "logexpdaylight") ("ver" . "2009,2010,2011,2012,2013,2014,2015,2016"))
                             (("name" . "logexpmidtones") ("ver" . "2009,2010,2011,2012,2013,2014,2015,2016"))
                             (("name" . "logexpphysicalscale") ("ver" . "2009,2010,2011,2012,2013,2014,2015,2016"))
                             (("name" . "logfilemode") ("ver" . "2009,2010,2011,2012,2013,2014,2015,2016"))
                             (("name" . "logfilename") ("ver" . "2009,2010,2011,2012,2013,2014,2015,2016"))
                             (("name" . "logfilepath") ("ver" . "2009,2010,2011,2012,2013,2014,2015,2016"))
                             (("name" . "loginname") ("ver" . "2009,2010,2011,2012,2013,2014,2015,2016"))
                             (("name" . "longitude") ("ver" . "2009,2010,2011,2012,2013,2014,2015,2016"))
                             (("name" . "ltscale") ("ver" . "2009,2010,2011,2012,2013,2014,2015,2016"))
                             (("name" . "lunits") ("ver" . "2009,2010,2011,2012,2013,2014,2015,2016"))
                             (("name" . "luprec") ("ver" . "2009,2010,2011,2012,2013,2014,2015,2016"))
                             (("name" . "lwdefault") ("ver" . "2009,2010,2011,2012,2013,2014,2015,2016"))
                             (("name" . "lwdisplay") ("ver" . "2009,2010,2011,2012,2013,2014,2015,2016"))
                             (("name" . "lwunits") ("ver" . "2009,2010,2011,2012,2013,2014,2015,2016"))
                             (("name" . "materialspath") ("ver" . "2011"))
                             (("name" . "maxactvp") ("ver" . "2009,2010,2011,2012,2013,2014,2015,2016"))
                             (("name" . "maxsort") ("ver" . "2009,2010,2011,2012,2013,2014,2015,2016"))
                             (("name" . "maxtouches") ("ver" . "2011,2012,2013,2014,2015,2016"))
                             (("name" . "mbuttonpan") ("ver" . "2009,2010,2011,2012,2013,2014,2015,2016"))
                             (("name" . "measureinit") ("ver" . "2009,2010,2011,2012,2013,2014,2015,2016"))
                             (("name" . "measurement") ("ver" . "2009,2010,2011,2012,2013,2014,2015,2016"))
                             (("name" . "menubar") ("ver" . "2009,2010,2011,2012,2013,2014,2015,2016"))
                             (("name" . "menuctl") ("ver" . "2009,2010,2011,2012,2013,2014,2015,2016"))
                             (("name" . "menuecho") ("ver" . "2009,2010,2011,2012,2013,2014,2015,2016"))
                             (("name" . "menuname") ("ver" . "2009,2010,2011,2012,2013,2014,2015,2016"))
                             (("name" . "meshtype") ("ver" . "2010,2011,2012,2013,2014,2015,2016"))
                             (("name" . "millisecs") ("ver" . "2009,2010,2011,2012,2013,2014,2015,2016"))
                             (("name" . "mirrhatch") ("ver" . "2011,2012,2013,2014,2015,2016"))
                             (("name" . "mirrtext") ("ver" . "2009,2010,2011,2012,2013,2014,2015,2016"))
                             (("name" . "mleaderscale") ("ver" . "2009,2010,2011,2012,2013,2014,2015,2016"))
                             (("name" . "modemacro") ("ver" . "2009,2010,2011,2012,2013,2014,2015,2016"))
                             (("name" . "msltscale") ("ver" . "2009,2010,2011,2012,2013,2014,2015,2016"))
                             (("name" . "msmstate") ("ver" . "2009,2010,2011,2012,2013,2014,2015,2016"))
                             (("name" . "msolescale") ("ver" . "2009,2010,2011,2012,2013,2014,2015,2016"))
                             (("name" . "mtextautostack") ("ver" . "2015,2016"))
                             (("name" . "mtextcolumn") ("ver" . "2010,2011,2012,2013,2014,2015,2016"))
                             (("name" . "mtextdetectspace") ("ver" . "2015,2016"))
                             (("name" . "mtexted") ("ver" . "2009,2010,2011,2012,2013,2014,2015,2016"))
                             (("name" . "mtextfixed") ("ver" . "2009,2010,2011,2012,2013,2014,2015,2016"))
                             (("name" . "mtexttoolbar") ("ver" . "2009,2010,2011,2012,2013,2014,2015,2016"))
                             (("name" . "mtjigstring") ("ver" . "2009,2010,2011,2012,2013,2014,2015,2016"))
                             (("name" . "mydocumentsprefix") ("ver" . "2009,2010,2011,2012,2013,2014,2015,2016"))
                             (("name" . "navbardisplay") ("ver" . "2011,2012,2013,2014,2015,2016"))
                             (("name" . "navswheelmode") ("ver" . "2009,2010,2011,2012,2013,2014,2015,2016"))
                             (("name" . "navswheelopacitybig") ("ver" . "2009,2010,2011,2012,2013,2014,2015,2016"))
                             (("name" . "navswheelopacitymini") ("ver" . "2009,2010,2011,2012,2013,2014,2015,2016"))
                             (("name" . "navswheelsizebig") ("ver" . "2009,2010,2011,2012,2013,2014,2015,2016"))
                             (("name" . "navswheelsizemini") ("ver" . "2009,2010,2011,2012,2013,2014,2015,2016"))
                             (("name" . "navvcubedisplay") ("ver" . "2009,2010,2011,2012,2013,2014,2015,2016"))
                             (("name" . "navvcubelocation") ("ver" . "2009,2010,2011,2012,2013,2014,2015,2016"))
                             (("name" . "navvcubeopacity") ("ver" . "2009,2010,2011,2012,2013,2014,2015,2016"))
                             (("name" . "navvcubeorient") ("ver" . "2009,2010,2011,2012,2013,2014,2015,2016"))
                             (("name" . "navvcubesize") ("ver" . "2009,2010,2011,2012,2013,2014,2015,2016"))
                             (("name" . "newtabmode") ("ver" . "2015"))
                             (("name" . "nextfiberworld") ("ver" . "2015"))
                             (("name" . "nfwstate") ("ver" . "2009,2010,2011,2012,2013,2014,2015,2016"))
                             (("name" . "nodename") ("ver" . "2009,2010,2011,2012,2013,2014,2015,2016"))
                             (("name" . "nomutt") ("ver" . "2009,2010,2011,2012,2013,2014,2015,2016"))
                             (("name" . "nopreviewgrip") ("ver" . "2013,2014"))
                             (("name" . "nopreviewhighlight") ("ver" . "2013,2014"))
                             (("name" . "northdirection") ("ver" . "2009,2010,2011,2012,2013,2014,2015,2016"))
                             (("name" . "objectisolationmode") ("ver" . "2011,2012,2013,2014,2015,2016"))
                             (("name" . "obscuredcolor") ("ver" . "2009,2010,2011,2012,2013,2014,2015,2016"))
                             (("name" . "obscuredltype") ("ver" . "2009,2010,2011,2012,2013,2014,2015,2016"))
                             (("name" . "offsetdist") ("ver" . "2009,2010,2011,2012,2013,2014,2015,2016"))
                             (("name" . "offsetgaptype") ("ver" . "2009,2010,2011,2012,2013,2014,2015,2016"))
                             (("name" . "oleframe") ("ver" . "2009,2010,2011,2012,2013,2014,2015,2016"))
                             (("name" . "olehide") ("ver" . "2009,2010,2011,2012,2013,2014,2015,2016"))
                             (("name" . "olequality") ("ver" . "2009,2010,2011,2012,2013,2014,2015,2016"))
                             (("name" . "olestartup") ("ver" . "2009,2010,2011,2012,2013,2014,2015,2016"))
                             (("name" . "onlineautosavepath") ("ver" . "2013"))
                             (("name" . "onlinedocmode") ("ver" . "2013,2014,2015"))
                             (("name" . "onlinedocuments") ("ver" . "2013"))
                             (("name" . "onlinefolder") ("ver" . "2013,2014,2015,2016"))
                             (("name" . "onlinesettingssync") ("ver" . "2013,2014,2015,2016"))
                             (("name" . "onlinesyncprovider") ("ver" . "2013,2014,2015,2016"))
                             (("name" . "onlinesynctime") ("ver" . "2013,2014,2015,2016"))
                             (("name" . "onlineuserid") ("ver" . "2014,2015,2016"))
                             (("name" . "onlineusername") ("ver" . "2013,2014,2015,2016"))
                             (("name" . "openpartial") ("ver" . "2009,2010,2011,2012,2013,2014,2015,2016"))
                             (("name" . "opmstate") ("ver" . "2009,2010,2011,2012,2013,2014,2015,2016"))
                             (("name" . "orbitautotarget") ("ver" . "2015,2016"))
                             (("name" . "orthomode") ("ver" . "2009,2010,2011,2012,2013,2014,2015,2016"))
                             (("name" . "osmode") ("ver" . "2009,2010,2011,2012,2013,2014,2015,2016"))
                             (("name" . "osnapcoord") ("ver" . "2009,2010,2011,2012,2013,2014,2015,2016"))
                             (("name" . "osnaphatch") ("ver" . "2009,2010,2011,2012,2013,2014,2015,2016"))
                             (("name" . "osnapnodelegacy") ("ver" . "2009,2010,2011,2012,2013,2014,2015,2016"))
                             (("name" . "osnapoverride") ("ver" . "2009,2010,2011,2012,2013,2014,2015,2016"))
                             (("name" . "osnapz") ("ver" . "2009,2010,2011,2012,2013,2014,2015,2016"))
                             (("name" . "osoptions") ("ver" . "2009,2010,2011,2012,2013,2014,2015,2016"))
                             (("name" . "paletteiconstate") ("ver" . "2013,2014,2015,2016"))
                             (("name" . "paletteopaque") ("ver" . "2009,2010,2011,2012,2013,2014,2015,2016"))
                             (("name" . "paperupdate") ("ver" . "2009,2010,2011,2012,2013,2014,2015,2016"))
                             (("name" . "parametercopymode") ("ver" . "2010,2011,2012,2013,2014,2015,2016"))
                             (("name" . "pcmstate") ("ver" . "2015,2016"))
                             (("name" . "pdfframe") ("ver" . "2009,2010,2011,2012,2013,2014,2015,2016"))
                             (("name" . "pdfosnap") ("ver" . "2009,2010,2011,2012,2013,2014,2015,2016"))
                             (("name" . "pdmode") ("ver" . "2009,2010,2011,2012,2013,2014,2015,2016"))
                             (("name" . "pdsize") ("ver" . "2009,2010,2011,2012,2013,2014,2015,2016"))
                             (("name" . "peditaccept") ("ver" . "2009,2010,2011,2012,2013,2014,2015,2016"))
                             (("name" . "pellipse") ("ver" . "2009,2010,2011,2012,2013,2014,2015,2016"))
                             (("name" . "perimeter") ("ver" . "2009,2010,2011,2012,2013,2014,2015,2016"))
                             (("name" . "perspective") ("ver" . "2009,2010,2011,2012,2013,2014,2015,2016"))
                             (("name" . "perspectiveclip") ("ver" . "2009,2010,2011,2012,2013,2014,2015,2016"))
                             (("name" . "pfacevmax") ("ver" . "2009,2010,2011,2012,2013,2014,2015,2016"))
                             (("name" . "phandle") ("ver" . "2009,2010,2011,2012,2013,2014,2015,2016"))
                             (("name" . "pickadd") ("ver" . "2009,2010,2011,2012,2013,2014,2015,2016"))
                             (("name" . "pickauto") ("ver" . "2009,2010,2011,2012,2013,2014,2015,2016"))
                             (("name" . "pickbox") ("ver" . "2009,2010,2011,2012,2013,2014,2015,2016"))
                             (("name" . "pickdrag") ("ver" . "2009,2010,2011,2012,2013,2014,2015,2016"))
                             (("name" . "pickfirst") ("ver" . "2009,2010,2011,2012,2013,2014,2015,2016"))
                             (("name" . "pickstyle") ("ver" . "2009,2010,2011,2012,2013,2014,2015,2016"))
                             (("name" . "platform") ("ver" . "2009,2010,2011,2012,2013,2014,2015,2016"))
                             (("name" . "plineconvertmode") ("ver" . "2009,2010,2011,2012,2013,2014,2015,2016"))
                             (("name" . "plinegen") ("ver" . "2009,2010,2011,2012,2013,2014,2015,2016"))
                             (("name" . "plinereversewidths") ("ver" . "2013,2014,2015,2016"))
                             (("name" . "plinetype") ("ver" . "2009,2010,2011,2012,2013,2014,2015,2016"))
                             (("name" . "plinewid") ("ver" . "2009,2010,2011,2012,2013,2014,2015,2016"))
                             (("name" . "plotid") ("ver" . "2009,2010,2011,2012,2013,2014,2015,2016"))
                             (("name" . "plotlegacy") ("ver" . "2009,2010,2011,2012,2013,2014,2015,2016"))
                             (("name" . "plotoffset") ("ver" . "2009,2010,2011,2012,2013,2014,2015,2016"))
                             (("name" . "plotrotmode") ("ver" . "2009,2010,2011,2012,2013,2014,2015,2016"))
                             (("name" . "plotter") ("ver" . "2009,2010,2011,2012,2013,2014,2015,2016"))
                             (("name" . "plottransparencyoverride") ("ver" . "2011,2012,2013,2014,2015,2016"))
                             (("name" . "plquiet") ("ver" . "2009,2010,2011,2012,2013,2014,2015,2016"))
                             (("name" . "pointcloud2dvsdisplay") ("ver" . "2016"))
                             (("name" . "pointcloudautoupdate") ("ver" . "2011,2012,2013,2014,2015,2016"))
                             (("name" . "pointcloudboundary") ("ver" . "2013,2014,2015,2016"))
                             (("name" . "pointcloudcachesize") ("ver" . "2014,2015,2016"))
                             (("name" . "pointcloudclipframe") ("ver" . "2013,2014,2015,2016"))
                             (("name" . "pointclouddensity") ("ver" . "2011,2012,2013,2014,2015,2016"))
                             (("name" . "pointcloudlighting") ("ver" . "2015,2016"))
                             (("name" . "pointcloudlightsource") ("ver" . "2015,2016"))
                             (("name" . "pointcloudlock") ("ver" . "2011,2012,2013,2014,2015,2016"))
                             (("name" . "pointcloudlod") ("ver" . "2015,2016"))
                             (("name" . "pointcloudpointmax") ("ver" . "2013,2014,2015,2016"))
                             (("name" . "pointcloudpointmaxlegacy") ("ver" . "2015,2016"))
                             (("name" . "pointcloudpointsize") ("ver" . "2015,2016"))
                             (("name" . "pointcloudrtdensity") ("ver" . "2011,2012,2013,2014,2015,2016"))
                             (("name" . "pointcloudshading") ("ver" . "2015,2016"))
                             (("name" . "pointcloudvisretain") ("ver" . "2014,2015,2016"))
                             (("name" . "polaraddang") ("ver" . "2009,2010,2011,2012,2013,2014,2015,2016"))
                             (("name" . "polarang") ("ver" . "2009,2010,2011,2012,2013,2014,2015,2016"))
                             (("name" . "polardist") ("ver" . "2009,2010,2011,2012,2013,2014,2015,2016"))
                             (("name" . "polarmode") ("ver" . "2009,2010,2011,2012,2013,2014,2015,2016"))
                             (("name" . "polysides") ("ver" . "2009,2010,2011,2012,2013,2014,2015,2016"))
                             (("name" . "popups") ("ver" . "2009,2010,2011,2012,2013,2014,2015,2016"))
                             (("name" . "preselectioneffect") ("ver" . "2015,2016"))
                             (("name" . "previewcreationtransparency") ("ver" . "2012,2013,2014,2015,2016"))
                             (("name" . "previewdelay") ("ver" . "2013,2014,2015,2016"))
                             (("name" . "previeweffect") ("ver" . "2009,2010,2011,2012,2013,2014"))
                             (("name" . "previewfaceeffect") ("ver" . "2011,2012,2013,2014"))
                             (("name" . "previewfilter") ("ver" . "2009,2010,2011,2012,2013,2014,2015,2016"))
                             (("name" . "previewtype") ("ver" . "2009,2010,2011,2012,2013,2014,2015,2016"))
                             (("name" . "product") ("ver" . "2009,2010,2011,2012,2013,2014,2015,2016"))
                             (("name" . "program") ("ver" . "2009,2010,2011,2012,2013,2014,2015,2016"))
                             (("name" . "projectname") ("ver" . "2009,2010,2011,2012,2013,2014,2015,2016"))
                             (("name" . "projmode") ("ver" . "2009,2010,2011,2012,2013,2014,2015,2016"))
                             (("name" . "propertypreview") ("ver" . "2013,2014,2015,2016"))
                             (("name" . "propobjlimit") ("ver" . "2012,2013,2014,2015,2016"))
                             (("name" . "propprevtimeout") ("ver" . "2013,2014,2015,2016"))
                             (("name" . "proxygraphics") ("ver" . "2009,2010,2011,2012,2013,2014,2015,2016"))
                             (("name" . "proxynotice") ("ver" . "2009,2010,2011,2012,2013,2014,2015,2016"))
                             (("name" . "proxyshow") ("ver" . "2009,2010,2011,2012,2013,2014,2015,2016"))
                             (("name" . "proxywebsearch") ("ver" . "2009,2010,2011,2012"))
                             (("name" . "psltscale") ("ver" . "2009,2010,2011,2012,2013,2014,2015,2016"))
                             (("name" . "psolheight") ("ver" . "2009,2010,2011,2012,2013,2014,2015,2016"))
                             (("name" . "psolwidth") ("ver" . "2009,2010,2011,2012,2013,2014,2015,2016"))
                             (("name" . "psprolog") ("ver" . "2009,2010,2011,2012,2013,2014,2015,2016"))
                             (("name" . "psquality") ("ver" . "2009,2010,2011,2012,2013,2014,2015,2016"))
                             (("name" . "pstylemode") ("ver" . "2009,2010,2011,2012,2013,2014,2015,2016"))
                             (("name" . "pstylepolicy") ("ver" . "2009,2010,2011,2012,2013,2014,2015,2016"))
                             (("name" . "psvpscale") ("ver" . "2009,2010,2011,2012,2013,2014,2015,2016"))
                             (("name" . "publishallsheets") ("ver" . "2009,2010,2011,2012,2013,2014,2015,2016"))
                             (("name" . "publishcollate") ("ver" . "2009,2010,2011,2012,2013,2014,2015,2016"))
                             (("name" . "publishhatch") ("ver" . "2009,2010,2011,2012,2013,2014,2015,2016"))
                             (("name" . "pucsbase") ("ver" . "2009,2010,2011,2012,2013,2014,2015,2016"))
                             (("name" . "qplocation") ("ver" . "2009,2010,2011,2012,2013,2014,2015,2016"))
                             (("name" . "qpmode") ("ver" . "2009,2010,2011,2012,2013,2014,2015,2016"))
                             (("name" . "qtextmode") ("ver" . "2009,2010,2011,2012,2013,2014,2015,2016"))
                             (("name" . "queuedregenmax") ("ver" . "2009,2010,2011,2012,2013,2014,2015,2016"))
                             (("name" . "qvdrawingpin") ("ver" . "2009,2010,2011,2012,2013,2014,2015,2016"))
                             (("name" . "qvlayoutpin") ("ver" . "2009,2010,2011,2012,2013,2014,2015,2016"))
                             (("name" . "rasterdpi") ("ver" . "2009,2010,2011,2012,2013,2014,2015,2016"))
                             (("name" . "rasterpercent") ("ver" . "2009,2010,2011,2012,2013,2014,2015,2016"))
                             (("name" . "rasterpreview") ("ver" . "2009,2010,2011,2012,2013,2014,2015,2016"))
                             (("name" . "rasterthreshold") ("ver" . "2009,2010,2011,2012,2013,2014,2015,2016"))
                             (("name" . "re-init") ("ver" . "2009,2010,2011,2012,2013,2014,2015,2016"))
                             (("name" . "rebuild2dcv") ("ver" . "2011,2012,2013,2014,2015,2016"))
                             (("name" . "rebuild2ddegree") ("ver" . "2011,2012,2013,2014,2015,2016"))
                             (("name" . "rebuild2doption") ("ver" . "2011,2012,2013,2014,2015,2016"))
                             (("name" . "rebuilddegreeu") ("ver" . "2011,2012,2013,2014,2015,2016"))
                             (("name" . "rebuilddegreev") ("ver" . "2011,2012,2013,2014,2015,2016"))
                             (("name" . "rebuildoptions") ("ver" . "2011,2012,2013,2014,2015,2016"))
                             (("name" . "rebuildu") ("ver" . "2011,2012,2013,2014,2015,2016"))
                             (("name" . "rebuildv") ("ver" . "2011,2012,2013,2014,2015,2016"))
                             (("name" . "recoverauto") ("ver" . "2011,2012,2013,2014,2015,2016"))
                             (("name" . "recoverymode") ("ver" . "2009,2010,2011,2012,2013,2014,2015,2016"))
                             (("name" . "refeditname") ("ver" . "2009,2010,2011,2012,2013,2014,2015,2016"))
                             (("name" . "regenmode") ("ver" . "2009,2010,2011,2012,2013,2014,2015,2016"))
                             (("name" . "rememberfolders") ("ver" . "2009,2010,2011,2012,2013,2014,2015,2016"))
                             (("name" . "renderlevel") ("ver" . "2016"))
                             (("name" . "renderlightcalc") ("ver" . "2016"))
                             (("name" . "renderquality") ("ver" . "2009,2010,2011,2012,2013,2014,2015,2016"))
                             (("name" . "rendertarget") ("ver" . "2016"))
                             (("name" . "rendertime") ("ver" . "2016"))
                             (("name" . "renderuserlights") ("ver" . "2009,2010,2011,2012,2013,2014,2015,2016"))
                             (("name" . "reporterror") ("ver" . "2009,2010,2011,2012,2013,2014,2015,2016"))
                             (("name" . "revcloudcreatemode") ("ver" . "2016"))
                             (("name" . "revcloudgrips") ("ver" . "2016"))
                             (("name" . "ribbonbgload") ("ver" . "2012,2013,2014,2015,2016"))
                             (("name" . "ribboncontextselect") ("ver" . "2010,2011,2012,2013,2014"))
                             (("name" . "ribboncontextsellim") ("ver" . "2010,2011,2012,2013,2014,2015,2016"))
                             (("name" . "ribbondockedheight") ("ver" . "2010,2011,2012,2013,2014,2015,2016"))
                             (("name" . "ribboniconresize") ("ver" . "2012,2013,2014,2015,2016"))
                             (("name" . "ribbonselectmode") ("ver" . "2010,2011,2012,2013,2014,2015,2016"))
                             (("name" . "ribbonstate") ("ver" . "2009,2010,2011,2012,2013,2014,2015,2016"))
                             (("name" . "roamablerootprefix") ("ver" . "2009,2010,2011,2012,2013,2014,2015,2016"))
                             (("name" . "rolloveropacity") ("ver" . "2011,2012,2013,2014,2015,2016"))
                             (("name" . "rollovertips") ("ver" . "2009,2010,2011,2012,2013,2014,2015,2016"))
                             (("name" . "rtdisplay") ("ver" . "2009,2010,2011,2012,2013,2014,2015,2016"))
                             (("name" . "safemode") ("ver" . "2014,2015,2016"))
                             (("name" . "savefidelity") ("ver" . "2009,2010,2011,2012,2013,2014,2015,2016"))
                             (("name" . "savefile") ("ver" . "2009,2010,2011,2012,2013,2014,2015,2016"))
                             (("name" . "savefilepath") ("ver" . "2009,2010,2011,2012,2013,2014,2015,2016"))
                             (("name" . "savename") ("ver" . "2009,2010,2011,2012,2013,2014,2015,2016"))
                             (("name" . "savetime") ("ver" . "2009,2010,2011,2012,2013,2014,2015,2016"))
                             (("name" . "screenboxes") ("ver" . "2009,2010,2011,2012,2013,2014,2015,2016"))
                             (("name" . "screenmenu") ("ver" . "2011"))
                             (("name" . "screenmode") ("ver" . "2009,2010,2011,2012,2013,2014,2015,2016"))
                             (("name" . "screensize") ("ver" . "2009,2010,2011,2012,2013,2014,2015,2016"))
                             (("name" . "sdi") ("ver" . "2009,2010,2011,2012,2013,2014,2015,2016"))
                             (("name" . "sectionoffsetinc") ("ver" . "2016"))
                             (("name" . "sectionthicknessinc") ("ver" . "2016"))
                             (("name" . "secureload") ("ver" . "2014,2015,2016"))
                             (("name" . "selectionannodisplay") ("ver" . "2009,2010,2011,2012,2013,2014,2015,2016"))
                             (("name" . "selectionarea") ("ver" . "2009,2010,2011,2012,2013,2014,2015,2016"))
                             (("name" . "selectionareaopacity") ("ver" . "2009,2010,2011,2012,2013,2014,2015,2016"))
                             (("name" . "selectioncycling") ("ver" . "2011,2012,2013,2014,2015,2016"))
                             (("name" . "selectioneffect") ("ver" . "2015,2016"))
                             (("name" . "selectioneffectcolor") ("ver" . "2016"))
                             (("name" . "selectionpreview") ("ver" . "2009,2010,2011,2012,2013,2014,2015,2016"))
                             (("name" . "selectionpreviewlimit") ("ver" . "2013,2014,2015,2016"))
                             (("name" . "selectsimilarmode") ("ver" . "2011,2012,2013,2014,2015,2016"))
                             (("name" . "setbylayermode") ("ver" . "2009,2010,2011,2012,2013,2014,2015,2016"))
                             (("name" . "shadedge") ("ver" . "2009,2010,2011,2012,2013,2014,2015,2016"))
                             (("name" . "shadedif") ("ver" . "2009,2010,2011,2012,2013,2014,2015,2016"))
                             (("name" . "shadowplanelocation") ("ver" . "2009,2010,2011,2012,2013,2014,2015,2016"))
                             (("name" . "shortcutmenu") ("ver" . "2009,2010,2011,2012,2013,2014,2015,2016"))
                             (("name" . "shortcutmenuduration") ("ver" . "2012,2013,2014,2015,2016"))
                             (("name" . "showhist") ("ver" . "2009,2010,2011,2012,2013,2014,2015,2016"))
                             (("name" . "showlayerusage") ("ver" . "2009,2010,2011,2012,2013,2014,2015,2016"))
                             (("name" . "showmotionpin") ("ver" . "2009,2010,2011,2012,2013,2014,2015,2016"))
                             (("name" . "showpagesetupfornewlayouts") ("ver" . "2012,2013,2014,2015,2016"))
                             (("name" . "shpname") ("ver" . "2009,2010,2011,2012,2013,2014,2015,2016"))
                             (("name" . "sigwarn") ("ver" . "2009,2010,2011,2012,2013,2014,2015,2016"))
                             (("name" . "sketchinc") ("ver" . "2009,2010,2011,2012,2013,2014,2015,2016"))
                             (("name" . "skpoly") ("ver" . "2009,2010,2011,2012,2013,2014,2015,2016"))
                             (("name" . "sktolerance") ("ver" . "2011,2012,2013,2014,2015,2016"))
                             (("name" . "skystatus") ("ver" . "2009,2010,2011,2012,2013,2014,2015,2016"))
                             (("name" . "smoothmeshconvert") ("ver" . "2010,2011,2012,2013,2014,2015,2016"))
                             (("name" . "smoothmeshgrid") ("ver" . "2010,2011,2012,2013,2014,2015,2016"))
                             (("name" . "smoothmeshmaxface") ("ver" . "2010,2011,2012,2013,2014,2015,2016"))
                             (("name" . "smoothmeshmaxlev") ("ver" . "2010,2011,2012,2013,2014,2015,2016"))
                             (("name" . "smstate") ("ver" . "2011,2012,2013,2014,2015,2016"))
                             (("name" . "snapang") ("ver" . "2009,2010,2011,2012,2013,2014,2015,2016"))
                             (("name" . "snapbase") ("ver" . "2009,2010,2011,2012,2013,2014,2015,2016"))
                             (("name" . "snapgridlegacy") ("ver" . "2012,2013,2014,2015,2016"))
                             (("name" . "snapisopair") ("ver" . "2009,2010,2011,2012,2013,2014,2015,2016"))
                             (("name" . "snapmode") ("ver" . "2009,2010,2011,2012,2013,2014,2015,2016"))
                             (("name" . "snapstyl") ("ver" . "2009,2010,2011,2012,2013,2014,2015,2016"))
                             (("name" . "snaptype") ("ver" . "2009,2010,2011,2012,2013,2014,2015,2016"))
                             (("name" . "snapunit") ("ver" . "2009,2010,2011,2012,2013,2014,2015,2016"))
                             (("name" . "solidcheck") ("ver" . "2009,2010,2011,2012,2013,2014,2015,2016"))
                             (("name" . "solidhist") ("ver" . "2009,2010,2011,2012,2013,2014,2015,2016"))
                             (("name" . "sortents") ("ver" . "2009,2010,2011,2012,2013,2014,2015,2016"))
                             (("name" . "sortorder") ("ver" . "2015,2016"))
                             (("name" . "spaceswitch") ("ver" . "2009,2010,2011,2012,2013,2014,2015,2016"))
                             (("name" . "spldegree") ("ver" . "2011,2012,2013,2014,2015,2016"))
                             (("name" . "splframe") ("ver" . "2009,2010,2011,2012,2013,2014,2015,2016"))
                             (("name" . "splinesegs") ("ver" . "2009,2010,2011,2012,2013,2014,2015,2016"))
                             (("name" . "splinetype") ("ver" . "2009,2010,2011,2012,2013,2014,2015,2016"))
                             (("name" . "splknots") ("ver" . "2011,2012,2013,2014,2015,2016"))
                             (("name" . "splmethod") ("ver" . "2011,2012,2013,2014,2015,2016"))
                             (("name" . "splperiodic") ("ver" . "2012,2013,2014,2015,2016"))
                             (("name" . "ssfound") ("ver" . "2009,2010,2011,2012,2013,2014,2015,2016"))
                             (("name" . "sslocate") ("ver" . "2009,2010,2011,2012,2013,2014,2015,2016"))
                             (("name" . "ssmautoopen") ("ver" . "2009,2010,2011,2012,2013,2014,2015,2016"))
                             (("name" . "ssmopenrefresh") ("ver" . "2009,2010,2011,2012,2013,2014,2015,2016"))
                             (("name" . "ssmpolltime") ("ver" . "2009,2010,2011,2012,2013,2014,2015,2016"))
                             (("name" . "ssmsheetstatus") ("ver" . "2009,2010,2011,2012,2013,2014,2015,2016"))
                             (("name" . "ssmstate") ("ver" . "2009,2010,2011,2012,2013,2014,2015,2016"))
                             (("name" . "standardsviolation") ("ver" . "2009,2010,2011,2012,2013,2014,2015,2016"))
                             (("name" . "startinfolder") ("ver" . "2013,2014,2015,2016"))
                             (("name" . "startmode") ("ver" . "2016"))
                             (("name" . "startup") ("ver" . "2009,2010,2011,2012,2013,2014,2015,2016"))
                             (("name" . "statusbar") ("ver" . "2009,2010,2011,2012,2013,2014,2015,2016"))
                             (("name" . "stepsize") ("ver" . "2009,2010,2011,2012,2013,2014,2015,2016"))
                             (("name" . "stepspersec") ("ver" . "2009,2010,2011,2012,2013,2014,2015,2016"))
                             (("name" . "stylesheet") ("ver" . "2009,2010,2011,2012,2013,2014,2015,2016"))
                             (("name" . "subobjselectionmode") ("ver" . "2010,2011,2012,2013,2014,2015,2016"))
                             (("name" . "sunstatus") ("ver" . "2009,2010,2011,2012,2013,2014,2015,2016"))
                             (("name" . "suppressalerts") ("ver" . "2013,2014,2015,2016"))
                             (("name" . "surfaceassociativity") ("ver" . "2011,2012,2013,2014,2015,2016"))
                             (("name" . "surfaceassociativitydrag") ("ver" . "2011,2012,2013,2014,2015,2016"))
                             (("name" . "surfaceautotrim") ("ver" . "2011,2012,2013,2014,2015,2016"))
                             (("name" . "surfacemodelingmode") ("ver" . "2011,2012,2013,2014,2015,2016"))
                             (("name" . "surfoffsetconnect") ("ver" . "2011,2012,2013,2014,2015,2016"))
                             (("name" . "surftab1") ("ver" . "2009,2010,2011,2012,2013,2014,2015,2016"))
                             (("name" . "surftab2") ("ver" . "2009,2010,2011,2012,2013,2014,2015,2016"))
                             (("name" . "surftrimautoextend") ("ver" . "2011,2012,2013,2014,2015,2016"))
                             (("name" . "surftrimprojection") ("ver" . "2011,2012,2013,2014,2015,2016"))
                             (("name" . "surftype") ("ver" . "2009,2010,2011,2012,2013,2014,2015,2016"))
                             (("name" . "surfu") ("ver" . "2009,2010,2011,2012,2013,2014,2015,2016"))
                             (("name" . "surfv") ("ver" . "2009,2010,2011,2012,2013,2014,2015,2016"))
                             (("name" . "syscodepage") ("ver" . "2009,2010,2011,2012,2013,2014,2015,2016"))
                             (("name" . "sysmon") ("ver" . "2016"))
                             (("name" . "tableindicator") ("ver" . "2009,2010,2011,2012,2013,2014,2015,2016"))
                             (("name" . "tabletoolbar") ("ver" . "2009,2010,2011,2012,2013,2014,2015,2016"))
                             (("name" . "tabmode") ("ver" . "2009,2010,2011,2012,2013,2014,2015,2016"))
                             (("name" . "target") ("ver" . "2009,2010,2011,2012,2013,2014,2015,2016"))
                             (("name" . "tbcustomize") ("ver" . "2009,2010,2011,2012,2013,2014,2015,2016"))
                             (("name" . "tbshowshortcuts") ("ver" . "2012,2013,2014,2015,2016"))
                             (("name" . "tdcreate") ("ver" . "2009,2010,2011,2012,2013,2014,2015,2016"))
                             (("name" . "tdindwg") ("ver" . "2009,2010,2011,2012,2013,2014,2015,2016"))
                             (("name" . "tducreate") ("ver" . "2009,2010,2011,2012,2013,2014,2015,2016"))
                             (("name" . "tdupdate") ("ver" . "2009,2010,2011,2012,2013,2014,2015,2016"))
                             (("name" . "tdusrtimer") ("ver" . "2009,2010,2011,2012,2013,2014,2015,2016"))
                             (("name" . "tduupdate") ("ver" . "2009,2010,2011,2012,2013,2014,2015,2016"))
                             (("name" . "tempoverrides") ("ver" . "2009,2010,2011,2012,2013,2014,2015,2016"))
                             (("name" . "tempprefix") ("ver" . "2009,2010,2011,2012,2013,2014,2015,2016"))
                             (("name" . "textalignmode") ("ver" . "2015,2016"))
                             (("name" . "textalignspacing") ("ver" . "2015,2016"))
                             (("name" . "textallcaps") ("ver" . "2015,2016"))
                             (("name" . "textautocorrectcaps") ("ver" . "2015,2016"))
                             (("name" . "texted") ("ver" . "2011,2012,2013,2014,2015,2016"))
                             (("name" . "texteditor") ("ver" . "2010,2011,2012,2013,2014,2015,2016"))
                             (("name" . "texteval") ("ver" . "2009,2010,2011,2012,2013,2014,2015,2016"))
                             (("name" . "textfill") ("ver" . "2009,2010,2011,2012,2013,2014,2015,2016"))
                             (("name" . "textjustify") ("ver" . "2014,2015,2016"))
                             (("name" . "textoutputfileformat") ("ver" . "2009,2010,2011,2012,2013,2014,2015,2016"))
                             (("name" . "textqlty") ("ver" . "2009,2010,2011,2012,2013,2014,2015,2016"))
                             (("name" . "textsize") ("ver" . "2009,2010,2011,2012,2013,2014,2015,2016"))
                             (("name" . "textstyle") ("ver" . "2009,2010,2011,2012,2013,2014,2015,2016"))
                             (("name" . "thickness") ("ver" . "2009,2010,2011,2012,2013,2014,2015,2016"))
                             (("name" . "thumbsave") ("ver" . "2013,2014,2015,2016"))
                             (("name" . "thumbsize") ("ver" . "2009,2010,2011,2012,2013,2014,2015,2016"))
                             (("name" . "tilemode") ("ver" . "2009,2010,2011,2012,2013,2014,2015,2016"))
                             (("name" . "timezone") ("ver" . "2009,2010,2011,2012,2013,2014,2015,2016"))
                             (("name" . "tooltipmerge") ("ver" . "2009,2010,2011,2012,2013,2014,2015,2016"))
                             (("name" . "tooltips") ("ver" . "2009,2010,2011,2012,2013,2014,2015,2016"))
                             (("name" . "tooltipsize") ("ver" . "2012,2013,2014,2015,2016"))
                             (("name" . "tooltiptransparency") ("ver" . "2012,2013,2014,2015,2016"))
                             (("name" . "touchmode") ("ver" . "2014,2015,2016"))
                             (("name" . "tpstate") ("ver" . "2009,2010,2011,2012,2013,2014,2015,2016"))
                             (("name" . "tracewid") ("ver" . "2009,2010,2011,2012,2013,2014,2015,2016"))
                             (("name" . "trackpath") ("ver" . "2009,2010,2011,2012,2013,2014,2015,2016"))
                             (("name" . "transparencydisplay") ("ver" . "2011,2012,2013,2014,2015,2016"))
                             (("name" . "trayicons") ("ver" . "2009,2010,2011,2012,2013,2014,2015,2016"))
                             (("name" . "traynotify") ("ver" . "2009,2010,2011,2012,2013,2014,2015,2016"))
                             (("name" . "traytimeout") ("ver" . "2009,2010,2011,2012,2013,2014,2015,2016"))
                             (("name" . "treedepth") ("ver" . "2009,2010,2011,2012,2013,2014,2015,2016"))
                             (("name" . "treemax") ("ver" . "2009,2010,2011,2012,2013,2014,2015,2016"))
                             (("name" . "trimmode") ("ver" . "2009,2010,2011,2012,2013,2014,2015,2016"))
                             (("name" . "trusteddomains") ("ver" . "2014,2015,2016"))
                             (("name" . "trustedpaths") ("ver" . "2014,2015,2016"))
                             (("name" . "tspacefac") ("ver" . "2009,2010,2011,2012,2013,2014,2015,2016"))
                             (("name" . "tspacetype") ("ver" . "2009,2010,2011,2012,2013,2014,2015,2016"))
                             (("name" . "tstackalign") ("ver" . "2009,2010,2011,2012,2013,2014,2015,2016"))
                             (("name" . "tstacksize") ("ver" . "2009,2010,2011,2012,2013,2014,2015,2016"))
                             (("name" . "ucs2ddisplaysetting") ("ver" . "2012,2013,2014,2015,2016"))
                             (("name" . "ucs3dparadisplaysetting") ("ver" . "2012,2013,2014,2015,2016"))
                             (("name" . "ucs3dperpdisplaysetting") ("ver" . "2012,2013,2014,2015,2016"))
                             (("name" . "ucsaxisang") ("ver" . "2009,2010,2011,2012,2013,2014,2015,2016"))
                             (("name" . "ucsbase") ("ver" . "2009,2010,2011,2012,2013,2014,2015,2016"))
                             (("name" . "ucsdetect") ("ver" . "2009,2010,2011,2012,2013,2014,2015,2016"))
                             (("name" . "ucsfollow") ("ver" . "2009,2010,2011,2012,2013,2014,2015,2016"))
                             (("name" . "ucsicon") ("ver" . "2009,2010,2011,2012,2013,2014,2015,2016"))
                             (("name" . "ucsname") ("ver" . "2009,2010,2011,2012,2013,2014,2015,2016"))
                             (("name" . "ucsorg") ("ver" . "2009,2010,2011,2012,2013,2014,2015,2016"))
                             (("name" . "ucsortho") ("ver" . "2009,2010,2011,2012,2013,2014,2015,2016"))
                             (("name" . "ucsselectmode") ("ver" . "2012,2013,2014,2015,2016"))
                             (("name" . "ucsview") ("ver" . "2009,2010,2011,2012,2013,2014,2015,2016"))
                             (("name" . "ucsvp") ("ver" . "2009,2010,2011,2012,2013,2014,2015,2016"))
                             (("name" . "ucsxdir") ("ver" . "2009,2010,2011,2012,2013,2014,2015,2016"))
                             (("name" . "ucsydir") ("ver" . "2009,2010,2011,2012,2013,2014,2015,2016"))
                             (("name" . "undoctl") ("ver" . "2009,2010,2011,2012,2013,2014,2015,2016"))
                             (("name" . "undomarks") ("ver" . "2009,2010,2011,2012,2013,2014,2015,2016"))
                             (("name" . "unitmode") ("ver" . "2009,2010,2011,2012,2013,2014,2015,2016"))
                             (("name" . "uosnap") ("ver" . "2010,2011,2012,2013,2014,2015,2016"))
                             (("name" . "updatethumbnail") ("ver" . "2009,2010,2011,2012,2013,2014,2015,2016"))
                             (("name" . "useri1") ("ver" . "2009,2010,2011,2012,2013,2014,2015,2016"))
                             (("name" . "useri2") ("ver" . "2009,2010,2011,2012,2013,2014,2015,2016"))
                             (("name" . "useri3") ("ver" . "2009,2010,2011,2012,2013,2014,2015,2016"))
                             (("name" . "useri4") ("ver" . "2009,2010,2011,2012,2013,2014,2015,2016"))
                             (("name" . "useri5") ("ver" . "2009,2010,2011,2012,2013,2014,2015,2016"))
                             (("name" . "userr1") ("ver" . "2009,2010,2011,2012,2013,2014,2015,2016"))
                             (("name" . "userr2") ("ver" . "2009,2010,2011,2012,2013,2014,2015,2016"))
                             (("name" . "userr3") ("ver" . "2009,2010,2011,2012,2013,2014,2015,2016"))
                             (("name" . "userr4") ("ver" . "2009,2010,2011,2012,2013,2014,2015,2016"))
                             (("name" . "userr5") ("ver" . "2009,2010,2011,2012,2013,2014,2015,2016"))
                             (("name" . "users1") ("ver" . "2009,2010,2011,2012,2013,2014,2015,2016"))
                             (("name" . "users2") ("ver" . "2009,2010,2011,2012,2013,2014,2015,2016"))
                             (("name" . "users3") ("ver" . "2009,2010,2011,2012,2013,2014,2015,2016"))
                             (("name" . "users4") ("ver" . "2009,2010,2011,2012,2013,2014,2015,2016"))
                             (("name" . "users5") ("ver" . "2009,2010,2011,2012,2013,2014,2015,2016"))
                             (("name" . "viewbackstatus") ("ver" . "2012,2013,2014,2015,2016"))
                             (("name" . "viewcreation") ("ver" . "2012,2013,2014,2015,2016"))
                             (("name" . "viewctr") ("ver" . "2009,2010,2011,2012,2013,2014,2015,2016"))
                             (("name" . "viewdetailcreation") ("ver" . "2013,2014,2015,2016"))
                             (("name" . "viewdetaileditor") ("ver" . "2013,2014,2015,2016"))
                             (("name" . "viewdir") ("ver" . "2009,2010,2011,2012,2013,2014,2015,2016"))
                             (("name" . "vieweditor") ("ver" . "2012,2013,2014,2015,2016"))
                             (("name" . "viewfwdstatus") ("ver" . "2012,2013,2014,2015,2016"))
                             (("name" . "viewmode") ("ver" . "2009,2010,2011,2012,2013,2014,2015,2016"))
                             (("name" . "viewsectioncreation") ("ver" . "2013,2014,2015,2016"))
                             (("name" . "viewsectioneditor") ("ver" . "2013,2014,2015,2016"))
                             (("name" . "viewsize") ("ver" . "2009,2010,2011,2012,2013,2014,2015,2016"))
                             (("name" . "viewsketchmode") ("ver" . "2013,2014,2015,2016"))
                             (("name" . "viewtwist") ("ver" . "2009,2010,2011,2012,2013,2014,2015,2016"))
                             (("name" . "viewupdateauto") ("ver" . "2013,2014,2015,2016"))
                             (("name" . "visretain") ("ver" . "2009,2010,2011,2012,2013,2014,2015,2016"))
                             (("name" . "vpcontrol") ("ver" . "2012,2013,2014,2015,2016"))
                             (("name" . "vplayeroverrides") ("ver" . "2009,2010,2011,2012,2013,2014,2015,2016"))
                             (("name" . "vplayeroverridesmode") ("ver" . "2009,2010,2011,2012,2013,2014,2015,2016"))
                             (("name" . "vpmaximizedstate") ("ver" . "2009,2010,2011,2012,2013,2014,2015,2016"))
                             (("name" . "vprotateassoc") ("ver" . "2009,2010,2011,2012,2013,2014,2015,2016"))
                             (("name" . "vsacurvaturehigh") ("ver" . "2011,2012,2013,2014,2015,2016"))
                             (("name" . "vsacurvaturelow") ("ver" . "2011,2012,2013,2014,2015,2016"))
                             (("name" . "vsacurvaturetype") ("ver" . "2011,2012,2013,2014,2015,2016"))
                             (("name" . "vsadraftanglehigh") ("ver" . "2011,2012,2013,2014,2015,2016"))
                             (("name" . "vsadraftanglelow") ("ver" . "2011,2012,2013,2014,2015,2016"))
                             (("name" . "vsazebracolor1") ("ver" . "2011,2012,2013,2014,2015,2016"))
                             (("name" . "vsazebracolor2") ("ver" . "2011,2012,2013,2014,2015,2016"))
                             (("name" . "vsazebradirection") ("ver" . "2011,2012,2013,2014,2015,2016"))
                             (("name" . "vsazebrasize") ("ver" . "2011,2012,2013,2014,2015,2016"))
                             (("name" . "vsazebratype") ("ver" . "2011,2012,2013,2014,2015,2016"))
                             (("name" . "vsbackgrounds") ("ver" . "2009,2010,2011,2012,2013,2014,2015,2016"))
                             (("name" . "vsedgecolor") ("ver" . "2009,2010,2011,2012,2013,2014,2015,2016"))
                             (("name" . "vsedgejitter") ("ver" . "2009,2010,2011,2012,2013,2014,2015,2016"))
                             (("name" . "vsedgelex") ("ver" . "2011,2012,2013,2014,2015,2016"))
                             (("name" . "vsedgeoverhang") ("ver" . "2009,2010,2011,2012,2013,2014,2015,2016"))
                             (("name" . "vsedges") ("ver" . "2009,2010,2011,2012,2013,2014,2015,2016"))
                             (("name" . "vsedgesmooth") ("ver" . "2009,2010,2011,2012,2013,2014,2015,2016"))
                             (("name" . "vsfacecolormode") ("ver" . "2009,2010,2011,2012,2013,2014,2015,2016"))
                             (("name" . "vsfacehighlight") ("ver" . "2009,2010,2011,2012,2013,2014,2015,2016"))
                             (("name" . "vsfaceopacity") ("ver" . "2009,2010,2011,2012,2013,2014,2015,2016"))
                             (("name" . "vsfacestyle") ("ver" . "2009,2010,2011,2012,2013,2014,2015,2016"))
                             (("name" . "vshalogap") ("ver" . "2009,2010,2011,2012,2013,2014,2015,2016"))
                             (("name" . "vshideprecision") ("ver" . "2009,2010,2011,2012,2013,2014,2015,2016"))
                             (("name" . "vsintersectioncolor") ("ver" . "2009,2010,2011,2012,2013,2014,2015,2016"))
                             (("name" . "vsintersectionedges") ("ver" . "2009,2010,2011,2012,2013,2014,2015,2016"))
                             (("name" . "vsintersectionltype") ("ver" . "2009,2010,2011,2012,2013,2014,2015,2016"))
                             (("name" . "vsisoontop") ("ver" . "2009,2010,2011,2012,2013,2014,2015,2016"))
                             (("name" . "vslightingquality") ("ver" . "2009,2010,2011,2012,2013,2014,2015,2016"))
                             (("name" . "vsmaterialmode") ("ver" . "2009,2010,2011,2012,2013,2014,2015,2016"))
                             (("name" . "vsmax") ("ver" . "2009,2010,2011,2012,2013,2014,2015,2016"))
                             (("name" . "vsmin") ("ver" . "2009,2010,2011,2012,2013,2014,2015,2016"))
                             (("name" . "vsmonocolor") ("ver" . "2009,2010,2011,2012,2013,2014,2015,2016"))
                             (("name" . "vsobscuredcolor") ("ver" . "2009,2010,2011,2012,2013,2014,2015,2016"))
                             (("name" . "vsobscurededges") ("ver" . "2009,2010,2011,2012,2013,2014,2015,2016"))
                             (("name" . "vsobscuredltype") ("ver" . "2009,2010,2011,2012,2013,2014,2015,2016"))
                             (("name" . "vsoccludedcolor") ("ver" . "2011,2012,2013,2014,2015,2016"))
                             (("name" . "vsoccludededges") ("ver" . "2011,2012,2013,2014,2015,2016"))
                             (("name" . "vsoccludedltype") ("ver" . "2011,2012,2013,2014,2015,2016"))
                             (("name" . "vsshadows") ("ver" . "2009,2010,2011,2012,2013,2014,2015,2016"))
                             (("name" . "vssilhedges") ("ver" . "2009,2010,2011,2012,2013,2014,2015,2016"))
                             (("name" . "vssilhwidth") ("ver" . "2009,2010,2011,2012,2013,2014,2015,2016"))
                             (("name" . "vtduration") ("ver" . "2009,2010,2011,2012,2013,2014,2015,2016"))
                             (("name" . "vtenable") ("ver" . "2009,2010,2011,2012,2013,2014,2015,2016"))
                             (("name" . "vtfps") ("ver" . "2009,2010,2011,2012,2013,2014,2015,2016"))
                             (("name" . "vtoolmotion") ("ver" . "2016"))
                             (("name" . "wbdefaultbrowser") ("ver" . "2011,2012,2013,2014,2015,2016"))
                             (("name" . "wbhelponline") ("ver" . "2011,2012,2013,2014,2015,2016"))
                             (("name" . "wbhelptype") ("ver" . "2011,2012,2013,2014,2015,2016"))
                             (("name" . "whiparc") ("ver" . "2009,2010,2011,2012,2013,2014,2015,2016"))
                             (("name" . "whipthread") ("ver" . "2009,2010,2011,2012,2013,2014,2015,2016"))
                             (("name" . "windowareacolor") ("ver" . "2009,2010,2011,2012,2013,2014,2015,2016"))
                             (("name" . "wipeoutframe") ("ver" . "2013,2014,2015,2016"))
                             (("name" . "wmfbkgnd") ("ver" . "2009,2010,2011,2012,2013,2014,2015,2016"))
                             (("name" . "wmfforegnd") ("ver" . "2009,2010,2011,2012,2013,2014,2015,2016"))
                             (("name" . "workingfolder") ("ver" . "2016"))
                             (("name" . "workspacelabel") ("ver" . "2012,2013,2014,2015,2016"))
                             (("name" . "worlducs") ("ver" . "2009,2010,2011,2012,2013,2014,2015,2016"))
                             (("name" . "worldview") ("ver" . "2009,2010,2011,2012,2013,2014,2015,2016"))
                             (("name" . "writestat") ("ver" . "2009,2010,2011,2012,2013,2014,2015,2016"))
                             (("name" . "wsautosave") ("ver" . "2011,2012,2013,2014,2015,2016"))
                             (("name" . "wscurrent") ("ver" . "2009,2010,2011,2012,2013,2014,2015,2016"))
                             (("name" . "xclipframe") ("ver" . "2009,2010,2011,2012,2013,2014,2015,2016"))
                             (("name" . "xdwgfadectl") ("ver" . "2010,2011,2012,2013,2014,2015,2016"))
                             (("name" . "xedit") ("ver" . "2009,2010,2011,2012,2013,2014,2015,2016"))
                             (("name" . "xfadectl") ("ver" . "2009,2010,2011,2012,2013,2014,2015,2016"))
                             (("name" . "xloadctl") ("ver" . "2009,2010,2011,2012,2013,2014,2015,2016"))
                             (("name" . "xloadpath") ("ver" . "2009,2010,2011,2012,2013,2014,2015,2016"))
                             (("name" . "xrefctl") ("ver" . "2009,2010,2011,2012,2013,2014,2015,2016"))
                             (("name" . "xrefnotify") ("ver" . "2009,2010,2011,2012,2013,2014,2015,2016"))
                             (("name" . "xrefoverride") ("ver" . "2016"))
                             (("name" . "xreftype") ("ver" . "2009,2010,2011,2012,2013,2014,2015,2016"))
                             (("name" . "zoomfactor") ("ver" . "2009,2010,2011,2012,2013,2014,2015,2016"))
                             (("name" . "zoomwheel") ("ver" . "2009,2010,2011,2012,2013,2014,2015,2016"))
                             )
      ) ;_ end of setq

(defun _kpblc-eval-value-round (value to)
                               ;|
;; http://forum.dwg.ru/showthread.php?p=301275
*    Выполняет округление числа до указанной точности
*    Примеры вызова:
(_kpblc-eval-value-round 16.365 0.01) ; 16.37
|;
  (if (zerop to)
    value
    (* (atoi (rtos (/ (float value) to) 2 0)) to)
    ) ;_ end of if
  ) ;_ end of defun

(defun _kpblc-conv-value-to-string (value /)
                                   ;|
*    конвертация значения в строку.
|;
  (cond
    ((= (type value) 'str) value)
    ((= (type value) 'int) (itoa value))
    ((and (= (type value) 'real)
          (equal value (_kpblc-eval-value-round value 1.) 1e-6)
          (equal value (fix value) 1e-6)
          ) ;_ end of and
     (itoa (fix value))
     )
    ((and (= (type value) 'real)
          (equal value (_kpblc-eval-value-round value 1.) 1e-6)
          (not (equal value (fix value) 1e-6))
          ) ;_ end of and
     (rtos value 2)
     )
    ((= (type value) 'real) (rtos value 2 14))
    ((not value) "")
    (t (vl-princ-to-string value))
    ) ;_ end of cond
  ) ;_ end of defun

(defun c:sysvarexport (/ file handle msg)
                      ;|
*    Команда экспортирует значения всех системных переменных в отдельный файл *.txt
|;
  (if (and (setq
             file (getfiled
                    "Введите имя файла для экспорта системных переменных"
                    ""
                    "txt"
                    1
                    ) ;_ end of getfiled
             ) ;_ end of setq
           (/= file)
           (setq handle (open file "w"))
           ) ;_ end of and
    (progn
      (foreach item *global-sysvar-list*
        (write-line
          (strcat (strcase (cdr (assoc "name" item)) t)
                  "="
                  (_kpblc-conv-value-to-string
                    (getvar (cdr (assoc "name" item)))
                    ) ;_ end of _kpblc-conv-value-to-string
                  ) ;_ end of strcat
          handle
          ) ;_ end of write-line
        ) ;_ end of foreach
      (close handle)
      (setq msg (cons "Данные сохранены в файле " file))
      (alert (strcat (car msg) "\n" (cdr msg)))
      (princ (strcat (car msg) " " (cdr msg)))
      ) ;_ end of progn
    ) ;_ end of if

  (princ)
  ) ;_ end of defun

(defun c:sysvardiff (/                    _kpblc-string-replace                     _kpblc-conv-list-to-string
                     _kpblc-conv-string-to-list                file                 handle
                     sysvar               str                  html_file            html_lst
                     f
                     )
                    ;|
*    Команда сравнивает имеющиеся в AutoCAD системные переменные и значения, сохраненные в стороннем
* txt-файле. Отчет выводится в виде html-страницы
|;

  (defun _kpblc-string-replace (str old new)
                               ;|
*    Функция замены вхождений подстроки на новую. Регистронезависима
*    Параметры вызова:
  str  исходная строка
  old  старая строка
  new  новая строка
*    Позволяет менять аналогичные строки: "str" -> "'_str'"
|;
    (_kpblc-conv-list-to-string
      (_kpblc-conv-string-to-list str old)
      new
      ) ;_ end of _kpblc-conv-list-to-string
    ) ;_ end of defun

  (defun _kpblc-conv-list-to-string (lst sep)
                                    ;|
*    Преобразование списка в строку
*    Параметры вызова:
  lst  обрабатываемй список
  sep  разделитель. nil -> " "
|;
    (if (and lst
             (setq lst (mapcar (function _kpblc-conv-value-to-string) lst))
             (setq sep (if sep
                         sep
                         " "
                         ) ;_ end of if
                   ) ;_ end of setq
             ) ;_ end of and
      (strcat (car lst)
              (apply (function strcat)
                     (mapcar
                       (function
                         (lambda (x)
                           (strcat sep x)
                           ) ;_ end of lambda
                         ) ;_ end of function
                       (cdr lst)
                       ) ;_ end of mapcar
                     ) ;_ end of apply
              ) ;_ end of strcat
      ""
      ) ;_ end of if
    ) ;_ end of defun

  (defun _kpblc-conv-string-to-list (string separator / i)
                                    ;|
*    Функция разбора строки. Возвращает список либо точечную пару. За основу взяты уроки Евгения Елпанова по рекурсиям
*    Параметры вызова:
*  string    разбираемая строка
*  separator  символ, используемый в качестве разделителя частей
*    Примеры вызова:
(_kpblc-conv-string-to-list "1;2;3;4;5;6" ";")  ;-> '(1 2 3 4 5 6)
(_kpblc-conv-string-to-list "1;2" ";")          ;-> '(1 2)
|;
    (cond
      ((= string "") nil)
      ((vl-string-search separator string)
       ((lambda (/ pos res)
          (while (setq pos (vl-string-search separator string))
            (setq res    (cons (substr string 1 pos) res)
                  string (substr string (+ (strlen separator) 1 pos))
                  ) ;_ end of setq
            ) ;_ end of while
          (reverse (cons string res))
          ) ;_ end of lambda
        )
       )
      ((wcmatch (strcase string)
                (strcat "*" (strcase separator) "*")
                ) ;_ end of wcmatch
       ((lambda (/ pos res _str prev)
          (setq pos  1
                prev 1
                _str (substr string pos)
                ) ;_ end of setq
          (while (<= pos (1+ (- (strlen string) (strlen separator))))
            (if
              (wcmatch (strcase (substr string pos (strlen separator)))
                       (strcase separator)
                       ) ;_ end of wcmatch
               (setq res    (cons (substr string 1 (1- pos)) res)
                     string (substr string (+ (strlen separator) pos))
                     pos    0
                     ) ;_ end of setq
               ) ;_ end of if
            (setq pos (1+ pos))
            ) ;_ end of while
          (if (< (strlen string) (strlen separator))
            (setq res (cons string res))
            ) ;_ end of if
          (if (or (not res) (= _str string))
            (setq res (list string))
            (reverse res)
            ) ;_ end of if
          ) ;_ end of lambda
        )
       )
      (t (list string))
      ) ;_ end of cond
    ) ;_ end of defun

  (if (and (setq file (getfiled
                        "Введите имя файла для сверки системных переменных"
                        ""
                        "txt"
                        4
                        ) ;_ end of getfiled
                 ) ;_ end of setq
           file
           (setq handle (open file "r"))
           ) ;_ end of and
    (progn
      (while (setq str (read-line handle))
        (setq
          sysvar (cons
                   (cons (substr str 1 (vl-string-search "=" str))
                         (substr str (+ 2 (vl-string-search "=" str)))
                         ) ;_ end of cons
                   sysvar
                   ) ;_ end of cons
          ) ;_ end of setq
        ) ;_ end of while
      (close handle)
      (if (setq
            sysvar (vl-sort (vl-remove-if
                              (function
                                (lambda (x)
                                  (or (not (getvar (car x)))
                                      (= (cdr x)
                                         (_kpblc-conv-value-to-string
                                           (getvar (car x))
                                           ) ;_ end of _kpblc-conv-value-to-string
                                         ) ;_ end of =
                                      ) ;_ end of or
                                  ) ;_ end of lambda
                                ) ;_ end of function
                              sysvar
                              ) ;_ end of vl-remove-if
                            (function
                              (lambda (a b)
                                (< (car a) (car b))
                                ) ;_ end of lambda
                              ) ;_ end of function
                            ) ;_ end of vl-sort
            ) ;_ end of setq
        (if (and (setq html_file (getfiled "Введите имя файла отчета"
                                           ""
                                           "html"
                                           1
                                           ) ;_ end of getfiled
                       ) ;_ end of setq
                 html_file
                 (setq handle (open html_file "w"))
                 ) ;_ end of and
          (progn
            (foreach item
                     (append
                       (list
                         "<html><head><title>Результаты сверки состояния системных переменных</title></head>"
                         (strcat
                           "<body><h1>Сверка системных переменных с файлом "
                           file
                           "</h1><br /><br />"
                           ) ;_ end of strcat
                         "<table cellspasing=\"0\" cellpadding=\"2\" width=\"100%\" border=\"1px\">"
                         "<tr style=\"text-align:center;\"><td width=\"20%\"><strong>Системная переменная</strong><td width=\"25%\"><strong>В файле txt</strong></td><td width=\"25%\"><strong>В AutoCAD</strong></td>"
                         "<td width=\"15%\">Доступна в версиях</td><td width=\"15%\">Сохраняется в</td></tr>"
                         ) ;_ end of list
                       (mapcar
                         (function
                           (lambda (x)
                             (strcat
                               "<tr"
                               (if (setq f (not f))
                                 ""
                                 " style=\"background-color: #e5e5e5;\""
                                 ) ;_ end of if
                               "><td>"
                               (car x)
                               "</td><td>"
                               (_kpblc-string-replace
                                 (_kpblc-string-replace
                                   (cdr x)
                                   "<"
                                   "&lt;"
                                   ) ;_ end of _kpblc-string-replace
                                 ">"
                                 "&gt;"
                                 ) ;_ end of _kpblc-string-replace
                               "</td><td  style=\"text-align:center;\">"
                               (_kpblc-string-replace
                                 (_kpblc-string-replace
                                   (_kpblc-conv-value-to-string
                                     (getvar (car x))
                                     ) ;_ end of _kpblc-conv-value-to-string
                                   "<"
                                   "&lt;"
                                   ) ;_ end of _kpblc-string-replace
                                 ">"
                                 "&gt;"
                                 ) ;_ end of _kpblc-string-replace
                               "</td>"
                               ;; Доступна в версиях
                               "<td>"
                               (cdr
                                 (assoc
                                   "ver"
                                   (car
                                     (vl-remove-if-not
                                       (function
                                         (lambda (x1)
                                           (= (strcase
                                                (cdr (assoc "name" x1))
                                                ) ;_ end of strcase
                                              (strcase (car x))
                                              ) ;_ end of =
                                           ) ;_ end of lambda
                                         ) ;_ end of function
                                       *global-sysvar-list*
                                       ) ;_ end of vl-remove-if-not
                                     ) ;_ end of car
                                   ) ;_ end of assoc
                                 ) ;_ end of cdr
                               "</td>"
                               ;; Сохраняется в...
                               "<td></td>"
                               "</tr>"
                               ) ;_ end of strcat
                             ) ;_ end of lambda
                           ) ;_ end of function
                         sysvar
                         ) ;_ end of mapcar
                       '("</table></body></html>")
                       ) ;_ end of append
              (write-line item handle)
              ) ;_ end of foreach
            (close handle)
            (command "_.browser" html_file)
            ) ;_ end of progn
          ) ;_ end of if
        (alert "Разница не обнаружена!")
        ) ;_ end of if
      ) ;_ end of progn
    ) ;_ end of if
  ) ;_ end of defun
