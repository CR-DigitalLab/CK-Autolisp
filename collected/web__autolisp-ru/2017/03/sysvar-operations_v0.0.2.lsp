;; v.0.0.2 Добавлены переменные acad 2017

(vl-load-com)

(setq *global-sysvar-list*
       '((("name" . "*_authorpalettepath") ("ver" . "2009,2010,2011,2012,2013,2014,2015,2016,2017"))
         (("name" . "*_linfo") ("ver" . "2009,2010,2011,2012,2013,2014,2015,2016"))
         (("name" . "*_toolpalettepath") ("ver" . "2009,2010,2011,2012,2013,2014,2015,2016,2017"))
         (("name" . "*acgidumpmode") ("ver" . "2009,2010,2011,2012,2013,2014,2015,2016,2017"))
         (("name" . "*annoselected") ("ver" . "2009,2010,2011,2012,2013,2014,2015,2016,2017"))
         (("name" . "*apstate") ("ver" . "2009,2010,2011,2012,2013,2014,2015,2016,2017"))
         (("name" . "*auxstat") ("ver" . "2009,2010,2011,2012,2013,2014,2015,2016,2017"))
         (("name" . "*axisunit") ("ver" . "2009,2010,2011,2012,2013,2014,2015,2016,2017"))
         (("name" . "*bgrdplottimeout") ("ver" . "2009,2010,2011,2012,2013,2014,2015,2016,2017"))
         (("name" . "*clistate") ("ver" . "2009,2010,2011,2012,2013,2014,2015,2016,2017"))
         (("name" . "*cputicks") ("ver" . "2009,2010,2011,2012,2013,2014,2015,2016,2017"))
         (("name" . "*dashboardstate") ("ver" . "2009,2010,2011,2012,2013,2014"))
         (("name" . "*dbcstate") ("ver" . "2009,2010,2011,2012,2013,2014,2015,2016,2017"))
         (("name" . "*defaultviewcategory") ("ver" . "2009,2010,2011,2012,2013,2014,2015,2016,2017"))
         (("name" . "*drstate") ("ver" . "2009,2010,2011,2012,2013,2014,2015,2016,2017"))
         (("name" . "*entexts") ("ver" . "2009,2010,2011,2012,2013,2014,2015,2016,2017"))
         (("name" . "*entmods") ("ver" . "2009,2010,2011,2012,2013,2014,2015,2016,2017"))
         (("name" . "*erstate") ("ver" . "2009,2010,2011,2012,2013,2014,2015,2016,2017"))
         (("name" . "*flatland") ("ver" . "2009,2010,2011,2012,2013,2014,2015,2016,2017"))
         (("name" . "*force_paging") ("ver" . "2009,2010,2011,2012,2013,2014,2015,2016,2017"))
         (("name" . "*globcheck") ("ver" . "2009,2010,2011,2012,2013,2014,2015,2016,2017"))
         (("name" . "*griplegacy") ("ver" . "2009,2010,2011,2012,2013,2014,2015,2016,2017"))
         (("name" . "*lazyload") ("ver" . "2009,2010,2011,2012,2013,2014,2015,2016,2017"))
         (("name" . "*lightliststate") ("ver" . "2009,2010,2011,2012,2013,2014,2015,2016,2017"))
         (("name" . "*lispinit") ("ver" . "2009,2010,2011,2012,2013,2014,2015,2016,2017"))
         (("name" . "*lispreset") ("ver" . "2009,2010,2011,2012,2013,2014,2015,2016,2017"))
         (("name" . "*macrotrace") ("ver" . "2009,2010,2011,2012,2013,2014,2015,2016,2017"))
         (("name" . "*matstate") ("ver" . "2009,2010,2011"))
         (("name" . "*maxobjmem") ("ver" . "2009,2010,2011,2012,2013,2014,2015,2016,2017"))
         (("name" . "*millisecs") ("ver" . "2009,2010,2011,2012,2013,2014,2015,2016,2017"))
         (("name" . "*msmstate") ("ver" . "2009,2010,2011,2012,2013,2014,2015,2016,2017"))
         (("name" . "*multicoremode") ("ver" . "2009,2010,2011,2012,2013,2014,2015,2016,2017"))
         (("name" . "*nfwstate") ("ver" . "2009,2010,2011,2012,2013,2014,2015,2016,2017"))
         (("name" . "*nodename") ("ver" . "2009,2010,2011,2012,2013,2014,2015,2016,2017"))
         (("name" . "*opmstate") ("ver" . "2009,2010,2011,2012,2013,2014,2015,2016,2017"))
         (("name" . "*osnapnodelegacy") ("ver" . "2009,2010,2011,2012,2013,2014,2015,2016,2017"))
         (("name" . "*product") ("ver" . "2009,2010,2011,2012,2013,2014,2015,2016,2017"))
         (("name" . "*program") ("ver" . "2009,2010,2011,2012,2013,2014,2015,2016,2017"))
         (("name" . "*qaflags") ("ver" . "2009,2010,2011,2012,2013,2014,2015,2016,2017"))
         (("name" . "*qaucslock") ("ver" . "2009,2010,2011,2012,2013,2014,2015,2016,2017"))
         (("name" . "*qcstate") ("ver" . "2009,2010,2011,2012,2013,2014,2015,2016,2017"))
         (("name" . "*queuedregenmax") ("ver" . "2009,2010,2011,2012,2013,2014,2015,2016,2017"))
         (("name" . "*r14rasterplot") ("ver" . "2009,2010,2011,2012,2013,2014,2015,2016,2017"))
         (("name" . "*renderprefsstate") ("ver" . "2009,2010,2011,2012,2013,2014,2015,2016,2017"))
         (("name" . "*selectlastmode") ("ver" . "2009,2010,2011,2012,2013,2014,2015,2016,2017"))
         (("name" . "*skip2dregens") ("ver" . "2009,2010,2011,2012,2013,2014,2015,2016,2017"))
         (("name" . "*spaceswitch") ("ver" . "2009,2010,2011,2012,2013,2014,2015,2016,2017"))
         (("name" . "*ssmstate") ("ver" . "2009,2010,2011,2012,2013,2014,2015,2016,2017"))
         (("name" . "*tbcustomize") ("ver" . "2009,2010,2011,2012,2013,2014,2015,2016,2017"))
         (("name" . "*tpstate") ("ver" . "2009,2010,2011,2012,2013,2014,2015,2016,2017"))
         (("name" . "*useacis") ("ver" . "2009,2010,2011,2012,2013,2014"))
         (("name" . "*whipthread") ("ver" . "2009,2010,2011,2012,2013,2014,2015,2016,2017"))
         (("name" . "-dwgunits") ("ver" . "2009,2010,2011,2012,2013,2014,2015,2016"))
         (("name" . "3dconversionmode") ("ver" . "2009,2010,2011,2012,2013,2014,2015,2016,2017"))
         (("name" . "3ddwfprec") ("ver" . "2009,2010,2011,2012,2013,2014,2015,2016,2017"))
         (("name" . "3dosmode") ("ver" . "2011,2012,2013,2014,2015,2016,2017"))
         (("name" . "3dosnap") ("ver" . "2011"))
         (("name" . "3dselectionmode") ("ver" . "2009,2010,2011,2012,2013LT,2013,2014,2015,2016,2017"))
         (("name" . "_authorpalettepath") ("ver" . "2009,2010,2011,2012,2013,2014,2015,2016,2017"))
         (("name" . "_linfo") ("ver" . "2009,2010,2011,2012,2013,2014,2015,2016"))
         (("name" . "_pkser") ("ver" . "2009,2010,2011,2012,2013,2014,2015,2016,2017"))
         (("name" . "_server") ("ver" . "2009,2010,2011,2012,2013,2014,2015,2016,2017"))
         (("name" . "_toolpalettepath") ("ver" . "2009,2010,2011,2012,2013,2014,2015,2016,2017"))
         (("name" . "_vernum") ("ver" . "2009,2010,2011,2012,2013,2014,2015,2016,2017"))
         (("name" . "acadlspasdoc") ("ver" . "2009,2010,2011,2012,2013,2014,2015,2016,2017"))
         (("name" . "acadprefix") ("ver" . "2009,2010,2011,2012,2013,2014,2015,2016,2017"))
         (("name" . "acadver") ("ver" . "2009,2010,2011,2012,2013,2014,2015,2016,2017"))
         (("name" . "acgidumpmode") ("ver" . "2009,2010,2011,2012,2013,2014,2015,2016,2017"))
         (("name" . "acisoutver") ("ver" . "2009,2010,2011,2012"))
         (("name" . "actpath") ("ver" . "2009,2010,2011,2012,2013,2014,2015,2016,2017"))
         (("name" . "actrecorderstate") ("ver" . "2009,2010,2011,2012,2013,2014,2015,2016,2017"))
         (("name" . "actrecpath") ("ver" . "2009,2010,2011,2012,2013,2014,2015,2016,2017"))
         (("name" . "actui") ("ver" . "2009,2010,2011,2012,2013,2014,2015,2016,2017"))
         (("name" . "adcstate") ("ver" . "2009,2010,2011,2012,2013,2014,2015,2016,2017"))
         (("name" . "aec3ddwfedge") ("ver" . "2012,2013,2014,2015,2016,2017"))
         (("name" . "aeceipinprogress") ("ver" . "2010,2011,2012,2013,2014,2015,2016,2017"))
         (("name" . "aecenableassocanchor") ("ver" . "2015,2016,2017"))
         (("name" . "aecenablesectioncleanup") ("ver" . "2015,2016,2017"))
         (("name" . "aecforcedefaultmodelview") ("ver" . "2012,2013,2014,2015,2016,2017"))
         (("name" . "aecforcedisplaybysizedisabled") ("ver" . "2012,2013,2014,2015,2016,2017"))
         (("name" . "aecforceexplodetosolid") ("ver" . "2012,2013,2014,2015,2016,2017"))
         (("name" . "aecobjectisolatemode") ("ver" . "2013,2014,2015,2016,2017"))
         (("name" . "aecpsdautoattach") ("ver" . "2014,2015,2016,2017"))
         (("name" . "aecpsdvisibility") ("ver" . "2016,2017"))
         (("name" . "aecvcompareignorehatch") ("ver" . "2015,2016,2017"))
         (("name" . "aecvcompareignoretext") ("ver" . "2015,2016,2017"))
         (("name" . "aecvcomparenewcolor") ("ver" . "2015,2016,2017"))
         (("name" . "aecvcompareoldcolor") ("ver" . "2015,2016,2017"))
         (("name" . "aecvcompareunchangedcolor") ("ver" . "2015,2016,2017"))
         (("name" . "aflags") ("ver" . "2009,2010,2011,2012,2013LT,2013,2014,2015,2016,2017"))
         (("name" . "angbase") ("ver" . "2009,2010,2011,2012,2013LT,2013,2014,2015,2016,2017"))
         (("name" . "angdir") ("ver" . "2009,2010,2011,2012,2013LT,2013,2014,2015,2016,2017"))
         (("name" . "annoallvisible") ("ver" . "2009,2010,2011,2012,2013LT,2013,2014,2015,2016,2017"))
         (("name" . "annoautoscale") ("ver" . "2009,2010,2011,2012,2013LT,2013,2014,2015,2016,2017"))
         (("name" . "annomonitor") ("ver" . "2013LT,2013,2014,2015,2016,2017"))
         (("name" . "annoselected") ("ver" . "2009,2010,2011,2012,2013,2014,2015,2016,2017"))
         (("name" . "annotativedwg") ("ver" . "2009,2010,2011,2012,2013LT,2013,2014,2015,2016,2017"))
         (("name" . "apbox") ("ver" . "2009,2010,2011,2012,2013LT,2013,2014,2015,2016,2017"))
         (("name" . "aperture") ("ver" . "2009,2010,2011,2012,2013LT,2013,2014,2015,2016,2017"))
         (("name" . "appautoload") ("ver" . "2012,2013,2014,2015,2016,2017"))
         (("name" . "appframeresources") ("ver" . "2010,2011,2012,2013,2014,2015,2016,2017"))
         (("name" . "applyglobalopacities") ("ver" . "2011,2012,2013,2014,2015,2016,2017"))
         (("name" . "apstate") ("ver" . "2009,2010,2011,2012,2013,2014,2015,2016,2017"))
         (("name" . "area") ("ver" . "2009,2010,2011,2012,2013LT,2013,2014,2015,2016,2017"))
         (("name" . "arrayassociativity") ("ver" . "2013LT,2013,2014,2015,2016,2017"))
         (("name" . "arraycreation") ("ver" . "2013,2014,2015,2016,2017"))
         (("name" . "arrayeditstate") ("ver" . "2012,2013LT,2013,2014,2015,2016,2017"))
         (("name" . "arraytype") ("ver" . "2012,2013LT,2013,2014,2015,2016,2017"))
         (("name" . "assiststate") ("ver" . "2009,2010,2011,2012,2013,2014,2015,2016"))
         (("name" . "attdia") ("ver" . "2009,2010,2011,2012,2013LT,2013,2014,2015,2016,2017"))
         (("name" . "attipe") ("ver" . "2009,2010,2011,2012,2013LT,2013,2014,2015,2016,2017"))
         (("name" . "attmode") ("ver" . "2009,2010,2011,2012,2013LT,2013,2014,2015,2016,2017"))
         (("name" . "attmulti") ("ver" . "2009,2010,2011,2012,2013LT,2013,2014,2015,2016,2017"))
         (("name" . "attreq") ("ver" . "2009,2010,2011,2012,2013LT,2013,2014,2015,2016,2017"))
         (("name" . "auditctl") ("ver" . "2009,2010,2011,2012,2013LT,2013,2014,2015,2016,2017"))
         (("name" . "aunits") ("ver" . "2009,2010,2011,2012,2013LT,2013,2014,2015,2016,2017"))
         (("name" . "auprec") ("ver" . "2009,2010,2011,2012,2013LT,2013,2014,2015,2016,2017"))
         (("name" . "autocompletedelay") ("ver" . "2012,2013LT,2013,2014,2015"))
         (("name" . "autocompletemode") ("ver" . "2012,2013LT,2013,2014,2015"))
         (("name" . "autodwfpublish") ("ver" . "2009,2010,2011,2012,2013LT,2013,2014,2015,2016,2017"))
         (("name" . "autoload") ("ver" . "2013"))
         (("name" . "autoloadpath") ("ver" . "2013"))
         (("name" . "automaticpub") ("ver" . "2010,2011,2012,2013LT,2013,2014,2015,2016,2017"))
         (("name" . "autosnap") ("ver" . "2009,2010,2011,2012,2013LT,2013,2014,2015,2016,2017"))
         (("name" . "auxstat") ("ver" . "2009,2010,2011,2012,2013,2014,2015,2016,2017"))
         (("name" . "axisunit") ("ver" . "2009,2010,2011,2012,2013,2014,2015,2016,2017"))
         (("name" . "backgroundplot") ("ver" . "2009,2010,2011,2012,2013LT,2013,2014,2015,2016,2017"))
         (("name" . "backz") ("ver" . "2009,2010,2011,2012,2013LT,2013,2014,2015,2016,2017"))
         (("name" . "bactionbarmode") ("ver" . "2010,2011,2012,2013LT,2013,2014,2015,2016,2017"))
         (("name" . "bactioncolor") ("ver" . "2009,2010,2011,2012,2013LT,2013,2014,2015,2016,2017"))
         (("name" . "bconstatusmode") ("ver" . "2010,2011,2012,2013LT,2013,2014,2015,2016,2017"))
         (("name" . "bdependencyhighlight") ("ver" . "2009,2010,2011,2012,2013LT,2013,2014,2015,2016,2017"))
         (("name" . "bgrdplottimeout") ("ver" . "2009,2010,2011,2012,2013,2014,2015,2016,2017"))
         (("name" . "bgripobjcolor") ("ver" . "2009,2010,2011,2012,2013LT,2013,2014,2015,2016,2017"))
         (("name" . "bgripobjsize") ("ver" . "2009,2010,2011,2012,2013LT,2013,2014,2015,2016,2017"))
         (("name" . "bindtype") ("ver" . "2009,2010,2011,2012,2013LT,2013,2014,2015,2016,2017"))
         (("name" . "blipmode") ("ver" . "2009,2010,2011,2012,2013,2014,2015,2016,2017"))
         (("name" . "blockeditlock") ("ver" . "2009,2010,2011,2012,2013LT,2013,2014,2015,2016,2017"))
         (("name" . "blockeditor") ("ver" . "2009,2010,2011,2012,2013LT,2013,2014,2015,2016,2017"))
         (("name" . "blocktestwindow") ("ver" . "2010,2011,2012,2013LT,2013,2014,2015,2016,2017"))
         (("name" . "bparametercolor") ("ver" . "2009,2010,2011,2012,2013LT,2013,2014,2015,2016,2017"))
         (("name" . "bparameterfont") ("ver" . "2009,2010,2011,2012,2013LT,2013,2014,2015,2016,2017"))
         (("name" . "bparametersize") ("ver" . "2009,2010,2011,2012,2013LT,2013,2014,2015,2016,2017"))
         (("name" . "bptexthorizontal") ("ver" . "2010,2011,2012,2013LT,2013,2014,2015,2016,2017"))
         (("name" . "btmarkdisplay") ("ver" . "2009,2010,2011,2012,2013LT,2013,2014,2015,2016,2017"))
         (("name" . "bvmode") ("ver" . "2009,2010,2011,2012,2013LT,2013,2014,2015,2016,2017"))
         (("name" . "cachemaxfiles") ("ver" . "2013LT,2013,2014,2015,2016,2017"))
         (("name" . "cachemaxtotalsize") ("ver" . "2013LT,2013,2014,2015,2016,2017"))
         (("name" . "calcinput") ("ver" . "2009,2010,2011,2012,2013LT,2013,2014,2015,2016,2017"))
         (("name" . "cameradisplay") ("ver" . "2009,2010,2011,2012,2013,2014,2015,2016,2017"))
         (("name" . "cameraheight") ("ver" . "2009,2010,2011,2012,2013,2014,2015,2016,2017"))
         (("name" . "cannoscale") ("ver" . "2009,2010,2011,2012,2013LT,2013,2014,2015,2016,2017"))
         (("name" . "cannoscalevalue") ("ver" . "2009,2010,2011,2012,2013LT,2013,2014,2015,2016,2017"))
         (("name" . "capturethumbnails") ("ver" . "2009,2010,2011,2012,2013,2014,2015,2016,2017"))
         (("name" . "cbardisplaymode") ("ver" . "2009"))
         (("name" . "cbartransparency") ("ver" . "2010,2011,2012,2013LT,2013,2014,2015,2016,2017"))
         (("name" . "cconstraintform") ("ver" . "2010,2011,2012,2013,2014,2015,2016,2017"))
         (("name" . "cdate") ("ver" . "2009,2010,2011,2012,2013LT,2013,2014,2015,2016,2017"))
         (("name" . "cdyndisplaymode") ("ver" . "2009,2010,2011,2012,2013,2014,2015,2016,2017"))
         (("name" . "cecolor") ("ver" . "2009,2010,2011,2012,2013LT,2013,2014,2015,2016,2017"))
         (("name" . "celtscale") ("ver" . "2009,2010,2011,2012,2013LT,2013,2014,2015,2016,2017"))
         (("name" . "celtype") ("ver" . "2009,2010,2011,2012,2013LT,2013,2014,2015,2016,2017"))
         (("name" . "celweight") ("ver" . "2009,2010,2011,2012,2013LT,2013,2014,2015,2016,2017"))
         (("name" . "centercrossgap") ("ver" . "2017"))
         (("name" . "centercrosssize") ("ver" . "2017"))
         (("name" . "centerexe") ("ver" . "2017"))
         (("name" . "centerlayer") ("ver" . "2017"))
         (("name" . "centerltscale") ("ver" . "2017"))
         (("name" . "centerltype") ("ver" . "2017"))
         (("name" . "centerltypefile") ("ver" . "2017"))
         (("name" . "centermarkexe") ("ver" . "2017"))
         (("name" . "centermt") ("ver" . "2009,2010,2011,2012,2013LT,2013,2014,2015,2016,2017"))
         (("name" . "cetransparency") ("ver" . "2011,2012,2013LT,2013,2014,2015,2016,2017"))
         (("name" . "cgeocs") ("ver" . "2014,2015,2016,2017"))
         (("name" . "chamfera") ("ver" . "2009,2010,2011,2012,2013LT,2013,2014,2015,2016,2017"))
         (("name" . "chamferb") ("ver" . "2009,2010,2011,2012,2013LT,2013,2014,2015,2016,2017"))
         (("name" . "chamferc") ("ver" . "2009,2010,2011,2012,2013LT,2013,2014,2015,2016,2017"))
         (("name" . "chamferd") ("ver" . "2009,2010,2011,2012,2013LT,2013,2014,2015,2016,2017"))
         (("name" . "chammode") ("ver" . "2009,2010,2011,2012,2013LT,2013,2014,2015,2016,2017"))
         (("name" . "cipmode") ("ver" . "2009,2010,2011,2012,2013LT,2013,2014,2015,2016"))
         (("name" . "circlerad") ("ver" . "2009,2010,2011,2012,2013LT,2013,2014,2015,2016,2017"))
         (("name" . "classickeys") ("ver" . "2011,2012,2013,2014,2015,2016,2017"))
         (("name" . "clayer") ("ver" . "2009,2010,2011,2012,2013LT,2013,2014,2015,2016,2017"))
         (("name" . "clayout") ("ver" . "2013LT,2014,2015,2016,2017"))
         (("name" . "cleanscreenstate") ("ver" . "2009,2010,2011,2012,2013LT,2013,2014,2015,2016,2017"))
         (("name" . "clipboard") ("ver" . "2013LT"))
         (("name" . "clipromptlines") ("ver" . "2013LT,2013,2014,2015,2016,2017"))
         (("name" . "clipromptupdate") ("ver" . "2013LT,2013,2014,2015,2016,2017"))
         (("name" . "cmaterial") ("ver" . "2009,2010,2011,2012,2013,2014,2015,2016,2017"))
         (("name" . "cmdactive") ("ver" . "2009,2010,2011,2012,2013LT,2013,2014,2015,2016,2017"))
         (("name" . "cmddia") ("ver" . "2009,2010,2011,2012,2013LT,2013,2014,2015,2016,2017"))
         (("name" . "cmdecho") ("ver" . "2009,2010,2011,2012,2013LT,2013,2014,2015,2016,2017"))
         (("name" . "cmdinputhistorymax") ("ver" . "2009,2010,2011,2012,2013LT,2013,2014,2015,2016,2017"))
         (("name" . "cmdnames") ("ver" . "2009,2010,2011,2012,2013LT,2013,2014,2015,2016,2017"))
         (("name" . "cmfadecolor") ("ver" . "2016,2017"))
         (("name" . "cmfadeopacity") ("ver" . "2016,2017"))
         (("name" . "cmleaderstyle") ("ver" . "2009,2010,2011,2012,2013LT,2013,2014,2015,2016,2017"))
         (("name" . "cmljust") ("ver" . "2009,2010,2011,2012,2013,2014,2015,2016,2017"))
         (("name" . "cmlscale") ("ver" . "2009,2010,2011,2012,2013,2014,2015,2016,2017"))
         (("name" . "cmlstyle") ("ver" . "2009,2010,2011,2012,2013,2014,2015,2016,2017"))
         (("name" . "cmosnap") ("ver" . "2017"))
         (("name" . "cnameformat") ("ver" . "2009"))
         (("name" . "colortheme") ("ver" . "2015,2016,2017"))
         (("name" . "commandpreview") ("ver" . "2015,2016,2017"))
         (("name" . "compass") ("ver" . "2009,2010,2011,2012,2013,2014,2015,2016,2017"))
         (("name" . "complexltpreview") ("ver" . "2015,2016,2017"))
         (("name" . "consolidationmode") ("ver" . "2017"))
         (("name" . "constraintbardisplay") ("ver" . "2010,2011,2012,2013,2014,2015,2016,2017"))
         (("name" . "constraintbarmode") ("ver" . "2010,2011,2012,2013LT,2013,2014,2015,2016,2017"))
         (("name" . "constraintcursordisplay") ("ver" . "2011,2012,2013,2014,2015,2016,2017"))
         (("name" . "constraintinfer") ("ver" . "2011,2012,2013,2014,2015,2016,2017"))
         (("name" . "constraintnameformat") ("ver" . "2010,2011,2012,2013LT,2013,2014,2015,2016,2017"))
         (("name" . "constraintrelax") ("ver" . "2009,2010,2011,2012,2013LT,2013,2014,2015,2016,2017"))
         (("name" . "constraintsolvemode") ("ver" . "2009,2010,2011,2012,2013LT,2013,2014,2015,2016,2017"))
         (("name" . "contentexplorerstate") ("ver" . "2013LT,2016"))
         (("name" . "coords") ("ver" . "2009,2010,2011,2012,2013LT,2013,2014,2015,2016,2017"))
         (("name" . "copymode") ("ver" . "2009,2010,2011,2012,2013LT,2013,2014,2015,2016,2017"))
         (("name" . "cplotstyle") ("ver" . "2009,2010,2011,2012,2013LT,2013,2014,2015,2016,2017"))
         (("name" . "cprofile") ("ver" . "2009,2010,2011,2012,2013,2014,2015,2016,2017"))
         (("name" . "cputicks") ("ver" . "2009,2010,2011,2012,2013,2014,2015,2016,2017"))
         (("name" . "crossingareacolor") ("ver" . "2009,2010,2011,2012,2013LT,2013,2014,2015,2016,2017"))
         (("name" . "cshadow") ("ver" . "2009,2010,2011,2012,2013,2014,2015,2016"))
         (("name" . "ctab") ("ver" . "2009,2010,2011,2012,2013LT,2013,2014,2015,2016,2017"))
         (("name" . "ctablestyle") ("ver" . "2009,2010,2011,2012,2013LT,2013,2014,2015,2016,2017"))
         (("name" . "cullingobj") ("ver" . "2011,2012,2013,2014,2015,2016,2017"))
         (("name" . "cullingobjselection") ("ver" . "2011,2012,2013,2014,2015,2016,2017"))
         (("name" . "currentprofile") ("ver" . "2009,2010,2011,2012,2013,2014,2015,2016"))
         (("name" . "cursorbadge") ("ver" . "2015,2016,2017"))
         (("name" . "cursorsize") ("ver" . "2009,2010,2011,2012,2013LT,2013,2014,2015,2016,2017"))
         (("name" . "cursortype") ("ver" . "2017"))
         (("name" . "cviewdetailstyle") ("ver" . "2013,2014,2015,2016,2017"))
         (("name" . "cviewsectionstyle") ("ver" . "2013,2014,2015,2016,2017"))
         (("name" . "cvport") ("ver" . "2009,2010,2011,2012,2013LT,2013,2014,2015,2016,2017"))
         (("name" . "datalinknotify") ("ver" . "2009,2010,2011,2012,2013LT,2013,2014,2015,2016,2017"))
         (("name" . "date") ("ver" . "2009,2010,2011,2012,2013LT,2013,2014,2015,2016,2017"))
         (("name" . "dbcstate") ("ver" . "2009,2010,2011,2012,2013,2014,2015,2016,2017"))
         (("name" . "dblclkedit") ("ver" . "2009,2010,2011,2012,2013LT,2013,2014,2015,2016,2017"))
         (("name" . "dbmod") ("ver" . "2009,2010,2011,2012,2013LT,2013,2014,2015,2016,2017"))
         (("name" . "dctcust") ("ver" . "2009,2010,2011,2012,2013LT,2013,2014,2015,2016,2017"))
         (("name" . "dctmain") ("ver" . "2009,2010,2011,2012,2013LT,2013,2014,2015,2016,2017"))
         (("name" . "defaultgizmo") ("ver" . "2010,2011,2012,2013,2014,2015,2016,2017"))
         (("name" . "defaultindex") ("ver" . "2010,2011,2012,2013,2014,2015,2016,2017"))
         (("name" . "defaultlighting") ("ver" . "2009,2010,2011,2012,2013,2014,2015,2016,2017"))
         (("name" . "defaultlightingtype") ("ver" . "2009,2010,2011,2012,2013,2014,2015,2016,2017"))
         (("name" . "defaultviewcategory") ("ver" . "2009,2010,2011,2012,2013,2014,2015,2016,2017"))
         (("name" . "deflplstyle") ("ver" . "2009,2010,2011,2012,2013LT,2013,2014,2015,2016,2017"))
         (("name" . "defplstyle") ("ver" . "2009,2010,2011,2012,2013LT,2013,2014,2015,2016,2017"))
         (("name" . "delobj") ("ver" . "2009,2010,2011,2012,2013LT,2013,2014,2015,2016,2017"))
         (("name" . "demandload") ("ver" . "2009,2010,2011,2012,2013,2014,2015,2016,2017"))
         (("name" . "designfeedstate") ("ver" . "2014,2015,2016,2017"))
         (("name" . "dgnframe") ("ver" . "2009,2010,2011,2012,2013LT,2013,2014,2015,2016,2017"))
         (("name" . "dgnimportmax") ("ver" . "2009,2010,2011,2012,2013LT,2013,2014,2015,2016,2017"))
         (("name" . "dgnimportmode") ("ver" . "2012,2013LT,2013,2014,2015,2016,2017"))
         (("name" . "dgnimportunitconversion") ("ver" . "2012,2013,2014,2015,2016,2017"))
         (("name" . "dgnmappingpath") ("ver" . "2009,2010,2011,2012,2013LT,2013,2014,2015,2016,2017"))
         (("name" . "dgnosnap") ("ver" . "2009,2010,2011,2012,2013LT,2013,2014,2015,2016,2017"))
         (("name" . "diastat") ("ver" . "2009,2010,2011,2012,2013LT,2013,2014,2015,2016,2017"))
         (("name" . "digitizer") ("ver" . "2011,2012,2013,2014,2015,2016,2017"))
         (("name" . "dimadec") ("ver" . "2009,2010,2011,2012,2013LT,2013,2014,2015,2016,2017"))
         (("name" . "dimalt") ("ver" . "2009,2010,2011,2012,2013LT,2013,2014,2015,2016,2017"))
         (("name" . "dimaltd") ("ver" . "2009,2010,2011,2012,2013LT,2013,2014,2015,2016,2017"))
         (("name" . "dimaltf") ("ver" . "2009,2010,2011,2012,2013LT,2013,2014,2015,2016,2017"))
         (("name" . "dimaltrnd") ("ver" . "2009,2010,2011,2012,2013LT,2013,2014,2015,2016,2017"))
         (("name" . "dimalttd") ("ver" . "2009,2010,2011,2012,2013LT,2013,2014,2015,2016,2017"))
         (("name" . "dimalttz") ("ver" . "2009,2010,2011,2012,2013LT,2013,2014,2015,2016,2017"))
         (("name" . "dimaltu") ("ver" . "2009,2010,2011,2012,2013LT,2013,2014,2015,2016,2017"))
         (("name" . "dimaltz") ("ver" . "2009,2010,2011,2012,2013LT,2013,2014,2015,2016,2017"))
         (("name" . "dimanno") ("ver" . "2009,2010,2011,2012,2013LT,2013,2014,2015,2016,2017"))
         (("name" . "dimapost") ("ver" . "2009,2010,2011,2012,2013LT,2013,2014,2015,2016,2017"))
         (("name" . "dimarcsym") ("ver" . "2009,2010,2011,2012,2013LT,2013,2014,2015,2016,2017"))
         (("name" . "dimaso") ("ver" . "2009,2010,2011,2012,2013LT,2013,2014,2015,2016,2017"))
         (("name" . "dimassoc") ("ver" . "2009,2010,2011,2012,2013LT,2013,2014,2015,2016,2017"))
         (("name" . "dimasz") ("ver" . "2009,2010,2011,2012,2013LT,2013,2014,2015,2016,2017"))
         (("name" . "dimatfit") ("ver" . "2009,2010,2011,2012,2013LT,2013,2014,2015,2016,2017"))
         (("name" . "dimaunit") ("ver" . "2009,2010,2011,2012,2013LT,2013,2014,2015,2016,2017"))
         (("name" . "dimazin") ("ver" . "2009,2010,2011,2012,2013LT,2013,2014,2015,2016,2017"))
         (("name" . "dimblk") ("ver" . "2009,2010,2011,2012,2013LT,2013,2014,2015,2016,2017"))
         (("name" . "dimblk1") ("ver" . "2009,2010,2011,2012,2013LT,2013,2014,2015,2016,2017"))
         (("name" . "dimblk2") ("ver" . "2009,2010,2011,2012,2013LT,2013,2014,2015,2016,2017"))
         (("name" . "dimcen") ("ver" . "2009,2010,2011,2012,2013LT,2013,2014,2015,2016,2017"))
         (("name" . "dimclrd") ("ver" . "2009,2010,2011,2012,2013LT,2013,2014,2015,2016,2017"))
         (("name" . "dimclre") ("ver" . "2009,2010,2011,2012,2013LT,2013,2014,2015,2016,2017"))
         (("name" . "dimclrt") ("ver" . "2009,2010,2011,2012,2013LT,2013,2014,2015,2016,2017"))
         (("name" . "dimconstrainticon") ("ver" . "2010,2011,2012,2013LT,2013,2014,2015,2016,2017"))
         (("name" . "dimcontinuemode") ("ver" . "2014,2015,2016,2017"))
         (("name" . "dimdec") ("ver" . "2009,2010,2011,2012,2013LT,2013,2014,2015,2016,2017"))
         (("name" . "dimdle") ("ver" . "2009,2010,2011,2012,2013LT,2013,2014,2015,2016,2017"))
         (("name" . "dimdli") ("ver" . "2009,2010,2011,2012,2013LT,2013,2014,2015,2016,2017"))
         (("name" . "dimdsep") ("ver" . "2009,2010,2011,2012,2013LT,2013,2014,2015,2016,2017"))
         (("name" . "dimexe") ("ver" . "2009,2010,2011,2012,2013LT,2013,2014,2015,2016,2017"))
         (("name" . "dimexo") ("ver" . "2009,2010,2011,2012,2013LT,2013,2014,2015,2016,2017"))
         (("name" . "dimfit") ("ver" . "2009,2010,2011,2012,2013LT,2013,2014,2015,2016,2017"))
         (("name" . "dimfrac") ("ver" . "2009,2010,2011,2012,2013LT,2013,2014,2015,2016,2017"))
         (("name" . "dimfxl") ("ver" . "2009,2010,2011,2012,2013LT,2013,2014,2015,2016,2017"))
         (("name" . "dimfxlon") ("ver" . "2009,2010,2011,2012,2013LT,2013,2014,2015,2016,2017"))
         (("name" . "dimgap") ("ver" . "2009,2010,2011,2012,2013LT,2013,2014,2015,2016,2017"))
         (("name" . "dimjogang") ("ver" . "2009,2010,2011,2012,2013LT,2013,2014,2015,2016,2017"))
         (("name" . "dimjust") ("ver" . "2009,2010,2011,2012,2013LT,2013,2014,2015,2016,2017"))
         (("name" . "dimlayer") ("ver" . "2016,2017"))
         (("name" . "dimldrblk") ("ver" . "2009,2010,2011,2012,2013LT,2013,2014,2015,2016,2017"))
         (("name" . "dimlfac") ("ver" . "2009,2010,2011,2012,2013LT,2013,2014,2015,2016,2017"))
         (("name" . "dimlim") ("ver" . "2009,2010,2011,2012,2013LT,2013,2014,2015,2016,2017"))
         (("name" . "dimltex1") ("ver" . "2009,2010,2011,2012,2013LT,2013,2014,2015,2016,2017"))
         (("name" . "dimltex2") ("ver" . "2009,2010,2011,2012,2013LT,2013,2014,2015,2016,2017"))
         (("name" . "dimltype") ("ver" . "2009,2010,2011,2012,2013LT,2013,2014,2015,2016,2017"))
         (("name" . "dimlunit") ("ver" . "2009,2010,2011,2012,2013LT,2013,2014,2015,2016,2017"))
         (("name" . "dimlwd") ("ver" . "2009,2010,2011,2012,2013LT,2013,2014,2015,2016,2017"))
         (("name" . "dimlwe") ("ver" . "2009,2010,2011,2012,2013LT,2013,2014,2015,2016,2017"))
         (("name" . "dimpickbox") ("ver" . "2016,2017"))
         (("name" . "dimpost") ("ver" . "2009,2010,2011,2012,2013LT,2013,2014,2015,2016,2017"))
         (("name" . "dimrnd") ("ver" . "2009,2010,2011,2012,2013LT,2013,2014,2015,2016,2017"))
         (("name" . "dimsah") ("ver" . "2009,2010,2011,2012,2013LT,2013,2014,2015,2016,2017"))
         (("name" . "dimscale") ("ver" . "2009,2010,2011,2012,2013LT,2013,2014,2015,2016,2017"))
         (("name" . "dimsd1") ("ver" . "2009,2010,2011,2012,2013LT,2013,2014,2015,2016,2017"))
         (("name" . "dimsd2") ("ver" . "2009,2010,2011,2012,2013LT,2013,2014,2015,2016,2017"))
         (("name" . "dimse1") ("ver" . "2009,2010,2011,2012,2013LT,2013,2014,2015,2016,2017"))
         (("name" . "dimse2") ("ver" . "2009,2010,2011,2012,2013LT,2013,2014,2015,2016,2017"))
         (("name" . "dimsho") ("ver" . "2009,2010,2011,2012,2013LT,2013,2014,2015,2016,2017"))
         (("name" . "dimsoxd") ("ver" . "2009,2010,2011,2012,2013LT,2013,2014,2015,2016,2017"))
         (("name" . "dimstyle") ("ver" . "2009,2010,2011,2012,2013LT,2013,2014,2015,2016,2017"))
         (("name" . "dimtad") ("ver" . "2009,2010,2011,2012,2013LT,2013,2014,2015,2016,2017"))
         (("name" . "dimtdec") ("ver" . "2009,2010,2011,2012,2013LT,2013,2014,2015,2016,2017"))
         (("name" . "dimtfac") ("ver" . "2009,2010,2011,2012,2013LT,2013,2014,2015,2016,2017"))
         (("name" . "dimtfill") ("ver" . "2009,2010,2011,2012,2013LT,2013,2014,2015,2016,2017"))
         (("name" . "dimtfillclr") ("ver" . "2009,2010,2011,2012,2013LT,2013,2014,2015,2016,2017"))
         (("name" . "dimtih") ("ver" . "2009,2010,2011,2012,2013LT,2013,2014,2015,2016,2017"))
         (("name" . "dimtix") ("ver" . "2009,2010,2011,2012,2013LT,2013,2014,2015,2016,2017"))
         (("name" . "dimtm") ("ver" . "2009,2010,2011,2012,2013LT,2013,2014,2015,2016,2017"))
         (("name" . "dimtmove") ("ver" . "2009,2010,2011,2012,2013LT,2013,2014,2015,2016,2017"))
         (("name" . "dimtofl") ("ver" . "2009,2010,2011,2012,2013LT,2013,2014,2015,2016,2017"))
         (("name" . "dimtoh") ("ver" . "2009,2010,2011,2012,2013LT,2013,2014,2015,2016,2017"))
         (("name" . "dimtol") ("ver" . "2009,2010,2011,2012,2013LT,2013,2014,2015,2016,2017"))
         (("name" . "dimtolj") ("ver" . "2009,2010,2011,2012,2013LT,2013,2014,2015,2016,2017"))
         (("name" . "dimtp") ("ver" . "2009,2010,2011,2012,2013LT,2013,2014,2015,2016,2017"))
         (("name" . "dimtsz") ("ver" . "2009,2010,2011,2012,2013LT,2013,2014,2015,2016,2017"))
         (("name" . "dimtvp") ("ver" . "2009,2010,2011,2012,2013LT,2013,2014,2015,2016,2017"))
         (("name" . "dimtxsty") ("ver" . "2009,2010,2011,2012,2013LT,2013,2014,2015,2016,2017"))
         (("name" . "dimtxt") ("ver" . "2009,2010,2011,2012,2013LT,2013,2014,2015,2016,2017"))
         (("name" . "dimtxtdirection") ("ver" . "2010,2011,2012,2013LT,2013,2014,2015,2016,2017"))
         (("name" . "dimtxtruler") ("ver" . "2016,2017"))
         (("name" . "dimtzin") ("ver" . "2009,2010,2011,2012,2013LT,2013,2014,2015,2016,2017"))
         (("name" . "dimunit") ("ver" . "2009,2010,2011,2012,2013LT,2013,2014,2015,2016,2017"))
         (("name" . "dimupt") ("ver" . "2009,2010,2011,2012,2013LT,2013,2014,2015,2016,2017"))
         (("name" . "dimzin") ("ver" . "2009,2010,2011,2012,2013LT,2013,2014,2015,2016,2017"))
         (("name" . "displayviewcubein2d") ("ver" . "2013,2014,2015,2016,2017"))
         (("name" . "displayviewcubein3d") ("ver" . "2015,2016,2017"))
         (("name" . "dispsilh") ("ver" . "2009,2010,2011,2012,2013LT,2013,2014,2015,2016,2017"))
         (("name" . "distance") ("ver" . "2009,2010,2011,2012,2013LT,2013,2014,2015,2016,2017"))
         (("name" . "divmeshboxheight") ("ver" . "2010,2011,2012,2013,2014,2015,2016,2017"))
         (("name" . "divmeshboxlength") ("ver" . "2010,2011,2012,2013,2014,2015,2016,2017"))
         (("name" . "divmeshboxwidth") ("ver" . "2010,2011,2012,2013,2014,2015,2016,2017"))
         (("name" . "divmeshconeaxis") ("ver" . "2010,2011,2012,2013,2014,2015,2016,2017"))
         (("name" . "divmeshconebase") ("ver" . "2010,2011,2012,2013,2014,2015,2016,2017"))
         (("name" . "divmeshconeheight") ("ver" . "2010,2011,2012,2013,2014,2015,2016,2017"))
         (("name" . "divmeshcylaxis") ("ver" . "2010,2011,2012,2013,2014,2015,2016,2017"))
         (("name" . "divmeshcylbase") ("ver" . "2010,2011,2012,2013,2014,2015,2016,2017"))
         (("name" . "divmeshcylheight") ("ver" . "2010,2011,2012,2013,2014,2015,2016,2017"))
         (("name" . "divmeshpyrbase") ("ver" . "2010,2011,2012,2013,2014,2015,2016,2017"))
         (("name" . "divmeshpyrheight") ("ver" . "2010,2011,2012,2013,2014,2015,2016,2017"))
         (("name" . "divmeshpyrlength") ("ver" . "2010,2011,2012,2013,2014,2015,2016,2017"))
         (("name" . "divmeshsphereaxis") ("ver" . "2010,2011,2012,2013,2014,2015,2016,2017"))
         (("name" . "divmeshsphereheight") ("ver" . "2010,2011,2012,2013,2014,2015,2016,2017"))
         (("name" . "divmeshtoruspath") ("ver" . "2010,2011,2012,2013,2014,2015,2016,2017"))
         (("name" . "divmeshtorussection") ("ver" . "2010,2011,2012,2013,2014,2015,2016,2017"))
         (("name" . "divmeshwedgebase") ("ver" . "2010,2011,2012,2013,2014,2015,2016,2017"))
         (("name" . "divmeshwedgeheight") ("ver" . "2010,2011,2012,2013,2014,2015,2016,2017"))
         (("name" . "divmeshwedgelength") ("ver" . "2010,2011,2012,2013,2014,2015,2016,2017"))
         (("name" . "divmeshwedgeslope") ("ver" . "2010,2011,2012,2013,2014,2015,2016,2017"))
         (("name" . "divmeshwedgewidth") ("ver" . "2010,2011,2012,2013,2014,2015,2016,2017"))
         (("name" . "donutid") ("ver" . "2009,2010,2011,2012,2013LT,2013,2014,2015,2016,2017"))
         (("name" . "donutod") ("ver" . "2009,2010,2011,2012,2013LT,2013,2014,2015,2016,2017"))
         (("name" . "dragmode") ("ver" . "2009,2010,2011,2012,2013LT,2013,2014,2015,2016,2017"))
         (("name" . "dragp1") ("ver" . "2009,2010,2011,2012,2013LT,2013,2014,2015,2016,2017"))
         (("name" . "dragp2") ("ver" . "2009,2010,2011,2012,2013LT,2013,2014,2015,2016,2017"))
         (("name" . "dragvs") ("ver" . "2009,2010,2011,2012,2013,2014,2015,2016,2017"))
         (("name" . "draworderctl") ("ver" . "2009,2010,2011,2012,2013LT,2013,2014,2015,2016,2017"))
         (("name" . "drstate") ("ver" . "2009,2010,2011,2012,2013,2014,2015,2016,2017"))
         (("name" . "dtexted") ("ver" . "2009,2010,2011,2012,2013LT,2013,2014,2015,2016,2017"))
         (("name" . "dwfframe") ("ver" . "2009,2010,2011,2012,2013LT,2013,2014,2015,2016,2017"))
         (("name" . "dwfosnap") ("ver" . "2009,2010,2011,2012,2013LT,2013,2014,2015,2016,2017"))
         (("name" . "dwgcheck") ("ver" . "2009,2010,2011,2012,2013LT,2013,2014,2015,2016,2017"))
         (("name" . "dwgcodepage") ("ver" . "2009,2010,2011,2012,2013LT,2013,2014,2015,2016,2017"))
         (("name" . "dwgname") ("ver" . "2009,2010,2011,2012,2013LT,2013,2014,2015,2016,2017"))
         (("name" . "dwgprefix") ("ver" . "2009,2010,2011,2012,2013LT,2013,2014,2015,2016,2017"))
         (("name" . "dwgtitled") ("ver" . "2009,2010,2011,2012,2013LT,2013,2014,2015,2016,2017"))
         (("name" . "dxeval") ("ver" . "2009,2010,2011,2012,2013,2014,2015,2016,2017"))
         (("name" . "dynconstraintdisplay") ("ver" . "2010,2011,2012,2013LT,2013,2014,2015,2016,2017"))
         (("name" . "dynconstraintmode") ("ver" . "2010,2011,2012,2013LT,2013,2014,2015,2016,2017"))
         (("name" . "dyndigrip") ("ver" . "2009,2010,2011,2012,2013LT,2013,2014,2015,2016,2017"))
         (("name" . "dyndivis") ("ver" . "2009,2010,2011,2012,2013LT,2013,2014,2015,2016,2017"))
         (("name" . "dyninfotips") ("ver" . "2012,2013LT,2013,2014,2015,2016,2017"))
         (("name" . "dynmode") ("ver" . "2009,2010,2011,2012,2013LT,2013,2014,2015,2016,2017"))
         (("name" . "dynpicoords") ("ver" . "2009,2010,2011,2012,2013LT,2013,2014,2015,2016,2017"))
         (("name" . "dynpiformat") ("ver" . "2009,2010,2011,2012,2013LT,2013,2014,2015,2016,2017"))
         (("name" . "dynpivis") ("ver" . "2009,2010,2011,2012,2013LT,2013,2014,2015,2016,2017"))
         (("name" . "dynprompt") ("ver" . "2009,2010,2011,2012,2013LT,2013,2014,2015,2016,2017"))
         (("name" . "dyntooltips") ("ver" . "2009,2010,2011,2012,2013LT,2013,2014,2015,2016,2017"))
         (("name" . "edgemode") ("ver" . "2009,2010,2011,2012,2013LT,2013,2014,2015,2016,2017"))
         (("name" . "elevation") ("ver" . "2009,2010,2011,2012,2013LT,2013,2014,2015,2016,2017"))
         (("name" . "enterprisemenu") ("ver" . "2009,2010,2011,2012,2013,2014,2015,2016,2017"))
         (("name" . "entexts") ("ver" . "2009,2010,2011,2012,2013,2014,2015,2016,2017"))
         (("name" . "entmods") ("ver" . "2009,2010,2011,2012,2013,2014,2015,2016,2017"))
         (("name" . "epdfshx") ("ver" . "2016,2017"))
         (("name" . "erhighlight") ("ver" . "2011,2012,2013LT,2013,2014,2015,2016,2017"))
         (("name" . "errno") ("ver" . "2009,2010,2011,2012,2013,2014,2015,2016,2017"))
         (("name" . "exedir") ("ver" . "2013LT"))
         (("name" . "expert") ("ver" . "2009,2010,2011,2012,2013LT,2013,2014,2015,2016,2017"))
         (("name" . "explmode") ("ver" . "2009,2010,2011,2012,2013LT,2013,2014,2015,2016,2017"))
         (("name" . "exporteplotformat") ("ver" . "2010,2011,2012,2013LT,2013,2014,2015,2016,2017"))
         (("name" . "exportmodelspace") ("ver" . "2010,2011,2012,2013LT,2013,2014,2015,2016,2017"))
         (("name" . "exportpagesetup") ("ver" . "2010,2011,2012,2013LT,2013,2014,2015,2016,2017"))
         (("name" . "exportpaperspace") ("ver" . "2010,2011,2012,2013LT,2013,2014,2015,2016,2017"))
         (("name" . "expvalue") ("ver" . "2016,2017"))
         (("name" . "expwhitebalance") ("ver" . "2016,2017"))
         (("name" . "extmax") ("ver" . "2009,2010,2011,2012,2013LT,2013,2014,2015,2016,2017"))
         (("name" . "extmin") ("ver" . "2009,2010,2011,2012,2013LT,2013,2014,2015,2016,2017"))
         (("name" . "extnames") ("ver" . "2009,2010,2011,2012,2013LT,2013,2014,2015,2016,2017"))
         (("name" . "faceterdevnormal") ("ver" . "2010,2011,2012,2013,2014,2015,2016,2017"))
         (("name" . "faceterdevsurface") ("ver" . "2010,2011,2012,2013,2014,2015,2016,2017"))
         (("name" . "facetergridratio") ("ver" . "2010,2011,2012,2013,2014,2015,2016,2017"))
         (("name" . "facetermaxedgelength") ("ver" . "2010,2011,2012,2013,2014,2015,2016,2017"))
         (("name" . "facetermaxgrid") ("ver" . "2010,2011,2012,2013,2014,2015,2016,2017"))
         (("name" . "facetermeshtype") ("ver" . "2010,2011,2012,2013,2014,2015,2016,2017"))
         (("name" . "faceterminugrid") ("ver" . "2010,2011,2012,2013,2014,2015,2016,2017"))
         (("name" . "faceterminvgrid") ("ver" . "2010,2011,2012,2013,2014,2015,2016,2017"))
         (("name" . "faceterprimitivemode") ("ver" . "2010,2011,2012,2013,2014,2015,2016,2017"))
         (("name" . "facetersmoothlev") ("ver" . "2010,2011,2012,2013,2014,2015,2016,2017"))
         (("name" . "facetratio") ("ver" . "2009,2010,2011,2012,2013,2014,2015,2016,2017"))
         (("name" . "facetres") ("ver" . "2009,2010,2011,2012,2013LT,2013,2014,2015,2016,2017"))
         (("name" . "fbximportlog") ("ver" . "2011,2012,2013,2014,2015,2016,2017"))
         (("name" . "fiberworld") ("ver" . "2015,2017"))
         (("name" . "fielddisplay") ("ver" . "2009,2010,2011,2012,2013LT,2013,2014,2015,2016,2017"))
         (("name" . "fieldeval") ("ver" . "2009,2010,2011,2012,2013LT,2013,2014,2015,2016,2017"))
         (("name" . "filedia") ("ver" . "2009,2010,2011,2012,2013LT,2013,2014,2015,2016,2017"))
         (("name" . "filetabpreview") ("ver" . "2014,2015,2016,2017"))
         (("name" . "filetabstate") ("ver" . "2014,2015,2016,2017"))
         (("name" . "filetabthumbhover") ("ver" . "2014,2015,2016,2017"))
         (("name" . "filletrad") ("ver" . "2009,2010,2011,2012,2013LT,2013,2014,2015,2016,2017"))
         (("name" . "filletrad3d") ("ver" . "2011,2012,2013,2014,2015,2016,2017"))
         (("name" . "fillmode") ("ver" . "2009,2010,2011,2012,2013LT,2013,2014,2015,2016,2017"))
         (("name" . "flatland") ("ver" . "2009,2010,2011,2012,2013,2014,2015,2016,2017"))
         (("name" . "fontalt") ("ver" . "2009,2010,2011,2012,2013LT,2013,2014,2015,2016,2017"))
         (("name" . "fontmap") ("ver" . "2009,2010,2011,2012,2013LT,2013,2014,2015,2016,2017"))
         (("name" . "force_paging") ("ver" . "2009,2010,2011,2012,2013,2014,2015,2016,2017"))
         (("name" . "frame") ("ver" . "2010,2011,2012,2013LT,2013,2014,2015,2016,2017"))
         (("name" . "frameselection") ("ver" . "2012,2013LT,2013,2014,2015,2016,2017"))
         (("name" . "frontz") ("ver" . "2009,2010,2011,2012,2013LT,2013,2014,2015,2016,2017"))
         (("name" . "fullopen") ("ver" . "2009,2010,2011,2012,2013,2014,2015,2016,2017"))
         (("name" . "fullplotpath") ("ver" . "2009,2010,2011,2012,2013LT,2013,2014,2015,2016,2017"))
         (("name" . "galleryview") ("ver" . "2016,2017"))
         (("name" . "geolatlongformat") ("ver" . "2009,2010,2011,2012,2013LT,2013,2014,2015,2016,2017"))
         (("name" . "geolocatemode") ("ver" . "2014,2015,2016,2017"))
         (("name" . "geomapmode") ("ver" . "2014,2015,2016,2017"))
         (("name" . "geomarkervisibility") ("ver" . "2009,2010,2011,2012,2013LT,2013,2014,2015,2016,2017"))
         (("name" . "geomarkpositionsize") ("ver" . "2014,2015,2016,2017"))
         (("name" . "gfang") ("ver" . "2009,2010,2011,2012,2013LT,2013,2014,2015,2016,2017"))
         (("name" . "gfclr1") ("ver" . "2009,2010,2011,2012,2013LT,2013,2014,2015,2016,2017"))
         (("name" . "gfclr2") ("ver" . "2009,2010,2011,2012,2013LT,2013,2014,2015,2016,2017"))
         (("name" . "gfclrlum") ("ver" . "2009,2010,2011,2012,2013LT,2013,2014,2015,2016,2017"))
         (("name" . "gfclrstate") ("ver" . "2009,2010,2011,2012,2013LT,2013,2014,2015,2016,2017"))
         (("name" . "gfname") ("ver" . "2009,2010,2011,2012,2013LT,2013,2014,2015,2016,2017"))
         (("name" . "gfshift") ("ver" . "2009,2010,2011,2012,2013LT,2013,2014,2015,2016,2017"))
         (("name" . "globalopacity") ("ver" . "2011,2012,2013,2014,2015,2016,2017"))
         (("name" . "globcheck") ("ver" . "2009,2010,2011,2012,2013,2014,2015,2016,2017"))
         (("name" . "griddisplay") ("ver" . "2009,2010,2011,2012,2013LT,2013,2014,2015,2016,2017"))
         (("name" . "gridmajor") ("ver" . "2009,2010,2011,2012,2013LT,2013,2014,2015,2016,2017"))
         (("name" . "gridmode") ("ver" . "2009,2010,2011,2012,2013LT,2013,2014,2015,2016,2017"))
         (("name" . "gridstyle") ("ver" . "2011,2012,2013LT,2013,2014,2015,2016,2017"))
         (("name" . "gridunit") ("ver" . "2009,2010,2011,2012,2013LT,2013,2014,2015,2016,2017"))
         (("name" . "gripblock") ("ver" . "2009,2010,2011,2012,2013LT,2013,2014,2015,2016,2017"))
         (("name" . "gripcolor") ("ver" . "2009,2010,2011,2012,2013LT,2013,2014,2015,2016,2017"))
         (("name" . "gripcontour") ("ver" . "2011,2012,2013LT,2013,2014,2015,2016,2017"))
         (("name" . "gripdyncolor") ("ver" . "2009,2010,2011,2012,2013LT,2013,2014,2015,2016,2017"))
         (("name" . "griphot") ("ver" . "2009,2010,2011,2012,2013LT,2013,2014,2015,2016,2017"))
         (("name" . "griphover") ("ver" . "2009,2010,2011,2012,2013LT,2013,2014,2015,2016,2017"))
         (("name" . "griplegacy") ("ver" . "2009,2010,2011,2012,2013,2014,2015,2016,2017"))
         (("name" . "gripmultifunctional") ("ver" . "2011,2012,2013LT,2013,2014,2015,2016,2017"))
         (("name" . "gripobjlimit") ("ver" . "2009,2010,2011,2012,2013LT,2013,2014,2015,2016,2017"))
         (("name" . "grips") ("ver" . "2009,2010,2011,2012,2013LT,2013,2014,2015,2016,2017"))
         (("name" . "gripsize") ("ver" . "2009,2010,2011,2012,2013LT,2013,2014,2015,2016,2017"))
         (("name" . "gripsubobjmode") ("ver" . "2010,2011,2012,2013,2014,2015,2016,2017"))
         (("name" . "griptips") ("ver" . "2009,2010,2011,2012,2013LT,2013,2014,2015,2016,2017"))
         (("name" . "groupdisplaymode") ("ver" . "2012,2013LT,2013,2014,2015,2016,2017"))
         (("name" . "gtauto") ("ver" . "2009,2010,2011,2012,2013,2014,2015,2016,2017"))
         (("name" . "gtdefault") ("ver" . "2009,2010,2011,2012,2013,2014,2015,2016,2017"))
         (("name" . "gtlocation") ("ver" . "2009,2010,2011,2012,2013,2014,2015,2016,2017"))
         (("name" . "halogap") ("ver" . "2009,2010,2011,2012,2013LT,2013,2014,2015,2016,2017"))
         (("name" . "handles") ("ver" . "2009,2010,2011,2012,2013LT,2013,2014,2015,2016,2017"))
         (("name" . "hatchboundset") ("ver" . "2011,2012,2013LT,2013,2014,2015,2016,2017"))
         (("name" . "hatchcreation") ("ver" . "2011,2012,2013LT,2013,2014,2015,2016,2017"))
         (("name" . "hatchtype") ("ver" . "2011,2012,2013LT,2013,2014,2015,2016,2017"))
         (("name" . "helpprefix") ("ver" . "2011,2012,2013,2014,2015,2016,2017"))
         (("name" . "hideprecision") ("ver" . "2009,2010,2011,2012,2013LT,2013,2014,2015,2016,2017"))
         (("name" . "hidetext") ("ver" . "2009,2010,2011,2012,2013LT,2013,2014,2015,2016,2017"))
         (("name" . "hidexrefscales") ("ver" . "2009,2010,2011,2012,2013LT,2013,2014,2015,2016,2017"))
         (("name" . "highlight") ("ver" . "2009,2010,2011,2012,2013LT,2013,2014,2015,2016,2017"))
         (("name" . "highlightsmoothing") ("ver" . "2015,2016,2017"))
         (("name" . "hpang") ("ver" . "2009,2010,2011,2012,2013LT,2013,2014,2015,2016,2017"))
         (("name" . "hpannotative") ("ver" . "2011,2012,2013LT,2013,2014,2015,2016,2017"))
         (("name" . "hpassoc") ("ver" . "2009,2010,2011,2012,2013LT,2013,2014,2015,2016,2017"))
         (("name" . "hpbackgroundcolor") ("ver" . "2011,2012,2013LT,2013,2014,2015,2016,2017"))
         (("name" . "hpbound") ("ver" . "2009,2010,2011,2012,2013LT,2013,2014,2015,2016,2017"))
         (("name" . "hpboundretain") ("ver" . "2011,2012,2013LT,2013,2014,2015,2016,2017"))
         (("name" . "hpcolor") ("ver" . "2011,2012,2013LT,2013,2014,2015,2016,2017"))
         (("name" . "hpdlgmode") ("ver" . "2011,2012,2013LT,2013,2014,2015,2016,2017"))
         (("name" . "hpdouble") ("ver" . "2009,2010,2011,2012,2013LT,2013,2014,2015,2016,2017"))
         (("name" . "hpdraworder") ("ver" . "2009,2010,2011,2012,2013LT,2013,2014,2015,2016,2017"))
         (("name" . "hpgaptol") ("ver" . "2009,2010,2011,2012,2013LT,2013,2014,2015,2016,2017"))
         (("name" . "hpinherit") ("ver" . "2009,2010,2011,2012,2013LT,2013,2014,2015,2016,2017"))
         (("name" . "hpislanddetection") ("ver" . "2011,2012,2013LT,2013,2014,2015,2016,2017"))
         (("name" . "hpislanddetectionmode") ("ver" . "2011,2012,2013LT,2013,2014,2015,2016,2017"))
         (("name" . "hplastpattern") ("ver" . "2011,2012,2013LT,2013,2014,2015,2016,2017"))
         (("name" . "hplayer") ("ver" . "2011,2012,2013LT,2013,2014,2015,2016,2017"))
         (("name" . "hplinetype") ("ver" . "2015,2016,2017"))
         (("name" . "hpmaxareas") ("ver" . "2012,2013LT,2013,2014,2015,2016,2017"))
         (("name" . "hpmaxlines") ("ver" . "2009,2010,2011,2012,2013LT,2013,2014,2015,2016,2017"))
         (("name" . "hpname") ("ver" . "2009,2010,2011,2012,2013LT,2013,2014,2015,2016,2017"))
         (("name" . "hpobjwarning") ("ver" . "2009,2010,2011,2012,2013LT,2013,2014,2015,2016,2017"))
         (("name" . "hporigin") ("ver" . "2009,2010,2011,2012,2013LT,2013,2014,2015,2016,2017"))
         (("name" . "hporiginmode") ("ver" . "2009,2010,2011,2012,2013LT,2013,2014,2015,2016,2017"))
         (("name" . "hporiginstoreasdefault") ("ver" . "2011,2012,2013,2014,2015,2016,2017"))
         (("name" . "hppickmode") ("ver" . "2014,2015,2016,2017"))
         (("name" . "hpquickpreview") ("ver" . "2011,2012,2013LT,2013,2014,2015,2016,2017"))
         (("name" . "hpquickprevtimeout") ("ver" . "2012,2013,2014,2015,2016,2017"))
         (("name" . "hprelativeps") ("ver" . "2011,2012,2013LT,2013,2014,2015,2016,2017"))
         (("name" . "hpscale") ("ver" . "2009,2010,2011,2012,2013LT,2013,2014,2015,2016,2017"))
         (("name" . "hpseparate") ("ver" . "2009,2010,2011,2012,2013LT,2013,2014,2015,2016,2017"))
         (("name" . "hpspace") ("ver" . "2009,2010,2011,2012,2013LT,2013,2014,2015,2016,2017"))
         (("name" . "hptransparency") ("ver" . "2011,2012,2013LT,2013,2014,2015,2016,2017"))
         (("name" . "hyperlinkbase") ("ver" . "2009,2010,2011,2012,2013LT,2013,2014,2015,2016,2017"))
         (("name" . "iblenvironment") ("ver" . "2016,2017"))
         (("name" . "imageframe") ("ver" . "2010,2011,2012,2013LT,2013,2014,2015,2016,2017"))
         (("name" . "imagehlt") ("ver" . "2009,2010,2011,2012,2013LT,2013,2014,2015,2016,2017"))
         (("name" . "impliedface") ("ver" . "2009,2010,2011,2012,2013,2014,2015,2016,2017"))
         (("name" . "indexctl") ("ver" . "2009,2010,2011,2012,2013LT,2013,2014,2015,2016,2017"))
         (("name" . "inetlocation") ("ver" . "2009,2010,2011,2012,2013LT,2013,2014,2015,2016,2017"))
         (("name" . "inputhistorymode") ("ver" . "2009,2010,2011,2012,2013LT,2013,2014,2015,2016,2017"))
         (("name" . "inputsearchdelay") ("ver" . "2014,2015,2016,2017"))
         (("name" . "insbase") ("ver" . "2009,2010,2011,2012,2013LT,2013,2014,2015,2016,2017"))
         (("name" . "insname") ("ver" . "2009,2010,2011,2012,2013LT,2013,2014,2015,2016,2017"))
         (("name" . "insunits") ("ver" . "2009,2010,2011,2012,2013LT,2013,2014,2015,2016,2017"))
         (("name" . "insunitsdefsource") ("ver" . "2009,2010,2011,2012,2013LT,2013,2014,2015,2016,2017"))
         (("name" . "insunitsdeftarget") ("ver" . "2009,2010,2011,2012,2013LT,2013,2014,2015,2016,2017"))
         (("name" . "intelligentupdate") ("ver" . "2009,2010,2011,2012,2013LT,2013,2014,2015,2016,2017"))
         (("name" . "interferecolor") ("ver" . "2009,2010,2011,2012,2013,2014,2015,2016,2017"))
         (("name" . "interfereobjvs") ("ver" . "2009,2010,2011,2012,2013,2014,2015,2016,2017"))
         (("name" . "interferevpvs") ("ver" . "2009,2010,2011,2012,2013,2014,2015,2016,2017"))
         (("name" . "intersectioncolor") ("ver" . "2009,2010,2011,2012,2013LT,2013,2014,2015,2016,2017"))
         (("name" . "intersectiondisplay") ("ver" . "2009,2010,2011,2012,2013LT,2013,2014,2015,2016,2017"))
         (("name" . "isavebak") ("ver" . "2009,2010,2011,2012,2013LT,2013,2014,2015,2016,2017"))
         (("name" . "isavepercent") ("ver" . "2009,2010,2011,2012,2013LT,2013,2014,2015,2016,2017"))
         (("name" . "isolines") ("ver" . "2009,2010,2011,2012,2013LT,2013,2014,2015,2016,2017"))
         (("name" . "largeobjectsupport") ("ver" . "2010,2011,2012,2013LT,2013,2014,2015,2016,2017"))
         (("name" . "lastangle") ("ver" . "2009,2010,2011,2012,2013LT,2013,2014,2015,2016,2017"))
         (("name" . "lastpoint") ("ver" . "2009,2010,2011,2012,2013LT,2013,2014,2015,2016,2017"))
         (("name" . "lastprompt") ("ver" . "2009,2010,2011,2012,2013,2014,2015,2016,2017"))
         (("name" . "latitude") ("ver" . "2009,2010,2011,2012,2013LT,2013,2014,2015,2016,2017"))
         (("name" . "layerdlgmode") ("ver" . "2009,2010,2011,2012,2013,2014,2015,2016,2017"))
         (("name" . "layereval") ("ver" . "2009,2010,2011,2012,2013LT,2013,2014,2015,2016,2017"))
         (("name" . "layerevalctl") ("ver" . "2009,2010,2011,2012,2013LT,2013,2014,2015,2016,2017"))
         (("name" . "layerfilteralert") ("ver" . "2009,2010,2011,2012,2013LT,2013,2014,2015,2016,2017"))
         (("name" . "layermanagerstate") ("ver" . "2009,2010,2011,2012,2013,2014,2015,2016,2017"))
         (("name" . "layernotify") ("ver" . "2009,2010,2011,2012,2013LT,2013,2014,2015,2016,2017"))
         (("name" . "laylockfadectl") ("ver" . "2009,2010,2011,2012,2013LT,2013,2014,2015,2016,2017"))
         (("name" . "layoutcreateviewport") ("ver" . "2012,2013LT,2013,2014,2015,2016,2017"))
         (("name" . "layoutregenctl") ("ver" . "2009,2010,2011,2012,2013,2014,2015,2016,2017"))
         (("name" . "layouttab") ("ver" . "2015,2016,2017"))
         (("name" . "lazyload") ("ver" . "2009,2010,2011,2012,2013,2014,2015,2016,2017"))
         (("name" . "legacycodesearch") ("ver" . "2016,2017"))
         (("name" . "legacyctrlpick") ("ver" . "2009,2010,2011,2012,2013,2014,2015,2016,2017"))
         (("name" . "lenslength") ("ver" . "2009,2010,2011,2012,2013LT,2013,2014,2015,2016,2017"))
         (("name" . "lightglyphdisplay") ("ver" . "2009,2010,2011,2012,2013,2014,2015,2016,2017"))
         (("name" . "lightingunits") ("ver" . "2009,2010,2011,2012,2013,2014,2015,2016,2017"))
         (("name" . "lightliststate") ("ver" . "2009,2010,2011,2012,2013,2014,2015,2016,2017"))
         (("name" . "lightsinblocks") ("ver" . "2009,2010,2011,2012,2013,2014,2015,2016,2017"))
         (("name" . "limcheck") ("ver" . "2009,2010,2011,2012,2013LT,2013,2014,2015,2016,2017"))
         (("name" . "limmax") ("ver" . "2009,2010,2011,2012,2013LT,2013,2014,2015,2016,2017"))
         (("name" . "limmin") ("ver" . "2009,2010,2011,2012,2013LT,2013,2014,2015,2016,2017"))
         (("name" . "linearbrightness") ("ver" . "2009,2010,2011,2012,2013,2014,2015,2016"))
         (("name" . "linearcontrast") ("ver" . "2009,2010,2011,2012,2013,2014,2015,2016"))
         (("name" . "linefading") ("ver" . "2015,2016,2017"))
         (("name" . "linefadinglevel") ("ver" . "2016,2017"))
         (("name" . "linesmoothing") ("ver" . "2015,2016,2017"))
         (("name" . "lispenabled") ("ver" . "2013"))
         (("name" . "lispinit") ("ver" . "2009,2010,2011,2012,2013,2014,2015,2016,2017"))
         (("name" . "locale") ("ver" . "2009,2010,2011,2012,2013LT,2013,2014,2015,2016,2017"))
         (("name" . "localrootprefix") ("ver" . "2009,2010,2011,2012,2013LT,2013,2014,2015,2016,2017"))
         (("name" . "lockui") ("ver" . "2009,2010,2011,2012,2013LT,2013,2014,2015,2016,2017"))
         (("name" . "loftang1") ("ver" . "2009,2010,2011,2012,2013,2014,2015,2016,2017"))
         (("name" . "loftang2") ("ver" . "2009,2010,2011,2012,2013,2014,2015,2016,2017"))
         (("name" . "loftmag1") ("ver" . "2009,2010,2011,2012,2013,2014,2015,2016,2017"))
         (("name" . "loftmag2") ("ver" . "2009,2010,2011,2012,2013,2014,2015,2016,2017"))
         (("name" . "loftnormals") ("ver" . "2009,2010,2011,2012,2013,2014,2015,2016,2017"))
         (("name" . "loftparam") ("ver" . "2009,2010,2011,2012,2013,2014,2015,2016,2017"))
         (("name" . "logexpbrightness") ("ver" . "2009,2010,2011,2012,2013,2014,2015,2016"))
         (("name" . "logexpcontrast") ("ver" . "2009,2010,2011,2012,2013,2014,2015,2016"))
         (("name" . "logexpdaylight") ("ver" . "2009,2010,2011,2012,2013,2014,2015,2016"))
         (("name" . "logexpmidtones") ("ver" . "2009,2010,2011,2012,2013,2014,2015,2016"))
         (("name" . "logexpphysicalscale") ("ver" . "2009,2010,2011,2012,2013,2014,2015,2016"))
         (("name" . "logfilemode") ("ver" . "2009,2010,2011,2012,2013LT,2013,2014,2015,2016,2017"))
         (("name" . "logfilename") ("ver" . "2009,2010,2011,2012,2013LT,2013,2014,2015,2016,2017"))
         (("name" . "logfilepath") ("ver" . "2009,2010,2011,2012,2013LT,2013,2014,2015,2016,2017"))
         (("name" . "loginname") ("ver" . "2009,2010,2011,2012,2013,2014,2015,2016,2017"))
         (("name" . "longitude") ("ver" . "2009,2010,2011,2012,2013LT,2013,2014,2015,2016,2017"))
         (("name" . "ltgapselection") ("ver" . "2017"))
         (("name" . "ltscale") ("ver" . "2009,2010,2011,2012,2013LT,2013,2014,2015,2016,2017"))
         (("name" . "lunits") ("ver" . "2009,2010,2011,2012,2013LT,2013,2014,2015,2016,2017"))
         (("name" . "luprec") ("ver" . "2009,2010,2011,2012,2013LT,2013,2014,2015,2016,2017"))
         (("name" . "lwdefault") ("ver" . "2009,2010,2011,2012,2013LT,2013,2014,2015,2016,2017"))
         (("name" . "lwdisplay") ("ver" . "2009,2010,2011,2012,2013LT,2013,2014,2015,2016,2017"))
         (("name" . "lwunits") ("ver" . "2009,2010,2011,2012,2013LT,2013,2014,2015,2016,2017"))
         (("name" . "macrotrace") ("ver" . "2009,2010,2011,2012,2013,2014,2015,2016,2017"))
         (("name" . "materialspath") ("ver" . "2011"))
         (("name" . "matstate") ("ver" . "2009,2010,2011"))
         (("name" . "maxactvp") ("ver" . "2009,2010,2011,2012,2013LT,2013,2014,2015,2016,2017"))
         (("name" . "maxobjmem") ("ver" . "2009,2010,2011,2012,2013,2014,2015,2016,2017"))
         (("name" . "maxsort") ("ver" . "2009,2010,2011,2012,2013LT,2013,2014,2015,2016,2017"))
         (("name" . "maxtouches") ("ver" . "2011,2012,2013,2014,2015,2016,2017"))
         (("name" . "mbuttonpan") ("ver" . "2009,2010,2011,2012,2013LT,2013,2014,2015,2016,2017"))
         (("name" . "measureinit") ("ver" . "2009,2010,2011,2012,2013LT,2013,2014,2015,2016,2017"))
         (("name" . "measurement") ("ver" . "2009,2010,2011,2012,2013LT,2013,2014,2015,2016,2017"))
         (("name" . "menubar") ("ver" . "2009,2010,2011,2012,2013LT,2013,2014,2015,2016,2017"))
         (("name" . "menuctl") ("ver" . "2009,2010,2011,2012,2013,2014,2015,2016,2017"))
         (("name" . "menuecho") ("ver" . "2009,2010,2011,2012,2013LT,2013,2014,2015,2016,2017"))
         (("name" . "menuname") ("ver" . "2009,2010,2011,2012,2013,2014,2015,2016,2017"))
         (("name" . "meshtype") ("ver" . "2010,2011,2012,2013,2014,2015,2016,2017"))
         (("name" . "millisecs") ("ver" . "2009,2010,2011,2012,2013,2014,2015,2016,2017"))
         (("name" . "mirrhatch") ("ver" . "2011,2012,2013LT,2013,2014,2015,2016,2017"))
         (("name" . "mirrtext") ("ver" . "2009,2010,2011,2012,2013LT,2013,2014,2015,2016,2017"))
         (("name" . "mleaderscale") ("ver" . "2009,2010,2011,2012,2013LT,2013,2014,2015,2016,2017"))
         (("name" . "modemacro") ("ver" . "2009,2010,2011,2012,2013LT,2013,2014,2015,2016,2017"))
         (("name" . "msltscale") ("ver" . "2009,2010,2011,2012,2013LT,2013,2014,2015,2016,2017"))
         (("name" . "msmstate") ("ver" . "2009,2010,2011,2012,2013,2014,2015,2016,2017"))
         (("name" . "msolescale") ("ver" . "2009,2010,2011,2012,2013LT,2013,2014,2015,2016,2017"))
         (("name" . "mtextautostack") ("ver" . "2015,2016,2017"))
         (("name" . "mtextcolumn") ("ver" . "2010,2011,2012,2013LT,2013,2014,2015,2016,2017"))
         (("name" . "mtextdetectspace") ("ver" . "2015,2016,2017"))
         (("name" . "mtexted") ("ver" . "2009,2010,2011,2012,2013LT,2013,2014,2015,2016,2017"))
         (("name" . "mtextfixed") ("ver" . "2009,2010,2011,2012,2013LT,2013,2014,2015,2016,2017"))
         (("name" . "mtexttoolbar") ("ver" . "2009,2010,2011,2012,2013LT,2013,2014,2015,2016,2017"))
         (("name" . "mtjigstring") ("ver" . "2009,2010,2011,2012,2013LT,2013,2014,2015,2016,2017"))
         (("name" . "multicoremode") ("ver" . "2009,2010,2011,2012,2013,2014,2015,2016,2017"))
         (("name" . "mydocumentsprefix") ("ver" . "2009,2010,2011,2012,2013LT,2013,2014,2015,2016,2017"))
         (("name" . "navbardisplay") ("ver" . "2011,2012,2013LT,2013,2014,2015,2016,2017"))
         (("name" . "navswheelmode") ("ver" . "2009,2010,2011,2012,2013,2014,2015,2016,2017"))
         (("name" . "navswheelopacitybig") ("ver" . "2009,2010,2011,2012,2013,2014,2015,2016,2017"))
         (("name" . "navswheelopacitymini") ("ver" . "2009,2010,2011,2012,2013,2014,2015,2016,2017"))
         (("name" . "navswheelsizebig") ("ver" . "2009,2010,2011,2012,2013,2014,2015,2016,2017"))
         (("name" . "navswheelsizemini") ("ver" . "2009,2010,2011,2012,2013,2014,2015,2016,2017"))
         (("name" . "navvcubedisplay") ("ver" . "2009,2010,2011,2012,2013,2014,2015,2016,2017"))
         (("name" . "navvcubelocation") ("ver" . "2009,2010,2011,2012,2013,2014,2015,2016,2017"))
         (("name" . "navvcubeopacity") ("ver" . "2009,2010,2011,2012,2013,2014,2015,2016,2017"))
         (("name" . "navvcubeorient") ("ver" . "2009,2010,2011,2012,2013,2014,2015,2016,2017"))
         (("name" . "navvcubesize") ("ver" . "2009,2010,2011,2012,2013,2014,2015,2016,2017"))
         (("name" . "newtabmode") ("ver" . "2015"))
         (("name" . "nextfiberworld") ("ver" . "2015,2017"))
         (("name" . "nfwstate") ("ver" . "2009,2010,2011,2012,2013,2014,2015,2016,2017"))
         (("name" . "nodename") ("ver" . "2009,2010,2011,2012,2013,2014,2015,2016,2017"))
         (("name" . "nomutt") ("ver" . "2009,2010,2011,2012,2013,2014,2015,2016,2017"))
         (("name" . "nopreviewgrip") ("ver" . "2013,2014"))
         (("name" . "nopreviewhighlight") ("ver" . "2013,2014"))
         (("name" . "northdirection") ("ver" . "2009,2010,2011,2012,2013LT,2013,2014,2015,2016,2017"))
         (("name" . "objectisolationmode") ("ver" . "2011,2012,2013LT,2013,2014,2015,2016,2017"))
         (("name" . "obscuredcolor") ("ver" . "2009,2010,2011,2012,2013LT,2013,2014,2015,2016,2017"))
         (("name" . "obscuredltype") ("ver" . "2009,2010,2011,2012,2013LT,2013,2014,2015,2016,2017"))
         (("name" . "offsetdist") ("ver" . "2009,2010,2011,2012,2013LT,2013,2014,2015,2016,2017"))
         (("name" . "offsetgaptype") ("ver" . "2009,2010,2011,2012,2013LT,2013,2014,2015,2016,2017"))
         (("name" . "oleframe") ("ver" . "2009,2010,2011,2012,2013LT,2013,2014,2015,2016,2017"))
         (("name" . "olehide") ("ver" . "2009,2010,2011,2012,2013LT,2013,2014,2015,2016,2017"))
         (("name" . "olequality") ("ver" . "2009,2010,2011,2012,2013LT,2013,2014,2015,2016,2017"))
         (("name" . "olestartup") ("ver" . "2009,2010,2011,2012,2013LT,2013,2014,2015,2016,2017"))
         (("name" . "onlineautosavepath") ("ver" . "2013LT,2013"))
         (("name" . "onlinedocmode") ("ver" . "2013LT,2013,2014,2015"))
         (("name" . "onlinedocuments") ("ver" . "2013LT,2013"))
         (("name" . "onlinefolder") ("ver" . "2013LT,2013,2014,2015,2016,2017"))
         (("name" . "onlinesettingssync") ("ver" . "2013LT,2013,2014,2015,2016,2017"))
         (("name" . "onlinesyncprovider") ("ver" . "2013LT,2013,2014,2015,2016,2017"))
         (("name" . "onlinesynctime") ("ver" . "2013LT,2013,2014,2015,2016,2017"))
         (("name" . "onlineuserid") ("ver" . "2014,2015,2016,2017"))
         (("name" . "onlineusername") ("ver" . "2013,2014,2015,2016,2017"))
         (("name" . "openpartial") ("ver" . "2009,2010,2011,2012,2013,2014,2015,2016,2017"))
         (("name" . "opmstate") ("ver" . "2009,2010,2011,2012,2013,2014,2015,2016,2017"))
         (("name" . "orbitautotarget") ("ver" . "2015,2016,2017"))
         (("name" . "orthomode") ("ver" . "2009,2010,2011,2012,2013LT,2013,2014,2015,2016,2017"))
         (("name" . "osmode") ("ver" . "2009,2010,2011,2012,2013LT,2013,2014,2015,2016,2017"))
         (("name" . "osnapcoord") ("ver" . "2009,2010,2011,2012,2013LT,2013,2014,2015,2016,2017"))
         (("name" . "osnaphatch") ("ver" . "2009,2010,2011,2012,2013LT,2013,2014,2015,2016,2017"))
         (("name" . "osnapnodelegacy") ("ver" . "2009,2010,2011,2012,2013,2014,2015,2016,2017"))
         (("name" . "osnapoverride") ("ver" . "2009,2010,2011,2012,2013,2014,2015,2016,2017"))
         (("name" . "osnapz") ("ver" . "2009,2010,2011,2012,2013,2014,2015,2016,2017"))
         (("name" . "osoptions") ("ver" . "2009,2010,2011,2012,2013LT,2013,2014,2015,2016,2017"))
         (("name" . "paletteiconstate") ("ver" . "2013,2014,2015,2016,2017"))
         (("name" . "paletteopaque") ("ver" . "2009,2010,2011,2012,2013LT,2013,2014,2015,2016,2017"))
         (("name" . "paperupdate") ("ver" . "2009,2010,2011,2012,2013LT,2013,2014,2015,2016,2017"))
         (("name" . "parametercopymode") ("ver" . "2010,2011,2012,2013,2014,2015,2016,2017"))
         (("name" . "pcmstate") ("ver" . "2015,2016,2017"))
         (("name" . "pdfframe") ("ver" . "2009,2010,2011,2012,2013LT,2013,2014,2015,2016,2017"))
         (("name" . "pdfimportfilter") ("ver" . "2017"))
         (("name" . "pdfimportimagepath") ("ver" . "2017"))
         (("name" . "pdfimportlayers") ("ver" . "2017"))
         (("name" . "pdfimportmode") ("ver" . "2017"))
         (("name" . "pdfosnap") ("ver" . "2009,2010,2011,2012,2013LT,2013,2014,2015,2016,2017"))
         (("name" . "pdmode") ("ver" . "2009,2010,2011,2012,2013LT,2013,2014,2015,2016,2017"))
         (("name" . "pdsize") ("ver" . "2009,2010,2011,2012,2013LT,2013,2014,2015,2016,2017"))
         (("name" . "peditaccept") ("ver" . "2009,2010,2011,2012,2013LT,2013,2014,2015,2016,2017"))
         (("name" . "pellipse") ("ver" . "2009,2010,2011,2012,2013LT,2013,2014,2015,2016,2017"))
         (("name" . "perimeter") ("ver" . "2009,2010,2011,2012,2013LT,2013,2014,2015,2016,2017"))
         (("name" . "perspective") ("ver" . "2009,2010,2011,2012,2013LT,2013,2014,2015,2016,2017"))
         (("name" . "perspectiveclip") ("ver" . "2009,2010,2011,2012,2013LT,2013,2014,2015,2016,2017"))
         (("name" . "pfacevmax") ("ver" . "2009,2010,2011,2012,2013,2014,2015,2016,2017"))
         (("name" . "phandle") ("ver" . "2009,2010,2011,2012,2013,2014,2015,2016,2017"))
         (("name" . "pickadd") ("ver" . "2009,2010,2011,2012,2013LT,2013,2014,2015,2016,2017"))
         (("name" . "pickauto") ("ver" . "2009,2010,2011,2012,2013LT,2013,2014,2015,2016,2017"))
         (("name" . "pickbox") ("ver" . "2009,2010,2011,2012,2013LT,2013,2014,2015,2016,2017"))
         (("name" . "pickdrag") ("ver" . "2009,2010,2011,2012,2013LT,2013,2014,2015,2016,2017"))
         (("name" . "pickfirst") ("ver" . "2009,2010,2011,2012,2013LT,2013,2014,2015,2016,2017"))
         (("name" . "pickstyle") ("ver" . "2009,2010,2011,2012,2013LT,2013,2014,2015,2016,2017"))
         (("name" . "platform") ("ver" . "2009,2010,2011,2012,2013LT,2013,2014,2015,2016,2017"))
         (("name" . "plineconvertmode") ("ver" . "2009,2010,2011,2012,2013LT,2013,2014,2015,2016,2017"))
         (("name" . "plinegcenmax") ("ver" . "2017"))
         (("name" . "plinegen") ("ver" . "2009,2010,2011,2012,2013LT,2013,2014,2015,2016,2017"))
         (("name" . "plinereversewidths") ("ver" . "2012,2013LT,2013,2014,2015,2016,2017"))
         (("name" . "plinetype") ("ver" . "2009,2010,2011,2012,2013LT,2013,2014,2015,2016,2017"))
         (("name" . "plinewid") ("ver" . "2009,2010,2011,2012,2013LT,2013,2014,2015,2016,2017"))
         (("name" . "plotid") ("ver" . "2009,2010,2011,2012,2013,2014,2015,2016"))
         (("name" . "plotlegacy") ("ver" . "2009,2010,2011,2012,2013,2014,2015,2016"))
         (("name" . "plotoffset") ("ver" . "2009,2010,2011,2012,2013LT,2013,2014,2015,2016,2017"))
         (("name" . "plotrotmode") ("ver" . "2009,2010,2011,2012,2013LT,2013,2014,2015,2016,2017"))
         (("name" . "plotter") ("ver" . "2009,2010,2011,2012,2013,2014,2015,2016"))
         (("name" . "plottransparencyoverride") ("ver" . "2011,2012,2013LT,2013,2014,2015,2016,2017"))
         (("name" . "plquiet") ("ver" . "2009,2010,2011,2012,2013LT,2013,2014,2015,2016,2017"))
         (("name" . "pointcloud2dvsdisplay") ("ver" . "2016,2017"))
         (("name" . "pointcloudautoupdate") ("ver" . "2011,2012,2013,2014,2015,2016,2017"))
         (("name" . "pointcloudboundary") ("ver" . "2013LT,2013,2014,2015,2016,2017"))
         (("name" . "pointcloudcachesize") ("ver" . "2014,2015,2016,2017"))
         (("name" . "pointcloudclipframe") ("ver" . "2013LT,2013,2014,2015,2016,2017"))
         (("name" . "pointclouddensity") ("ver" . "2011,2012,2013LT,2013,2014,2015,2016,2017"))
         (("name" . "pointcloudlighting") ("ver" . "2015,2016,2017"))
         (("name" . "pointcloudlightsource") ("ver" . "2015,2016,2017"))
         (("name" . "pointcloudlock") ("ver" . "2011,2012,2013,2014,2015,2016,2017"))
         (("name" . "pointcloudlod") ("ver" . "2015,2016,2017"))
         (("name" . "pointcloudpointmax") ("ver" . "2013,2014,2015,2016,2017"))
         (("name" . "pointcloudpointmaxlegacy") ("ver" . "2015,2016,2017"))
         (("name" . "pointcloudpointsize") ("ver" . "2015,2016,2017"))
         (("name" . "pointcloudrtdensity") ("ver" . "2011,2012,2013,2014,2015,2016,2017"))
         (("name" . "pointcloudshading") ("ver" . "2015,2016,2017"))
         (("name" . "pointcloudvisretain") ("ver" . "2014,2015,2016,2017"))
         (("name" . "polaraddang") ("ver" . "2009,2010,2011,2012,2013LT,2013,2014,2015,2016,2017"))
         (("name" . "polarang") ("ver" . "2009,2010,2011,2012,2013LT,2013,2014,2015,2016,2017"))
         (("name" . "polardist") ("ver" . "2009,2010,2011,2012,2013LT,2013,2014,2015,2016,2017"))
         (("name" . "polarmode") ("ver" . "2009,2010,2011,2012,2013LT,2013,2014,2015,2016,2017"))
         (("name" . "polysides") ("ver" . "2009,2010,2011,2012,2013LT,2013,2014,2015,2016,2017"))
         (("name" . "popups") ("ver" . "2009,2010,2011,2012,2013,2014,2015,2016,2017"))
         (("name" . "preselectioneffect") ("ver" . "2015,2016,2017"))
         (("name" . "previewcreationtransparency") ("ver" . "2012,2013,2014,2015,2016,2017"))
         (("name" . "previewdelay") ("ver" . "2013,2014,2015,2016,2017"))
         (("name" . "previeweffect") ("ver" . "2009,2010,2011,2012,2013LT,2013,2014"))
         (("name" . "previewfaceeffect") ("ver" . "2011,2012,2013,2014"))
         (("name" . "previewfilter") ("ver" . "2009,2010,2011,2012,2013LT,2013,2014,2015,2016,2017"))
         (("name" . "previewtype") ("ver" . "2009,2010,2011,2012,2013,2014,2015,2016,2017"))
         (("name" . "product") ("ver" . "2009,2010,2011,2012,2013,2014,2015,2016,2017"))
         (("name" . "program") ("ver" . "2009,2010,2011,2012,2013,2014,2015,2016,2017"))
         (("name" . "projectname") ("ver" . "2009,2010,2011,2012,2013,2014,2015,2016,2017"))
         (("name" . "projmode") ("ver" . "2009,2010,2011,2012,2013LT,2013,2014,2015,2016,2017"))
         (("name" . "propertypreview") ("ver" . "2013LT,2013,2014,2015,2016,2017"))
         (("name" . "propobjlimit") ("ver" . "2012,2013LT,2013,2014,2015,2016,2017"))
         (("name" . "propprevtimeout") ("ver" . "2013,2014,2015,2016,2017"))
         (("name" . "proxygraphics") ("ver" . "2009,2010,2011,2012,2013LT,2013,2014,2015,2016,2017"))
         (("name" . "proxynotice") ("ver" . "2009,2010,2011,2012,2013LT,2013,2014,2015,2016,2017"))
         (("name" . "proxyshow") ("ver" . "2009,2010,2011,2012,2013LT,2013,2014,2015,2016,2017"))
         (("name" . "proxywebsearch") ("ver" . "2009,2010,2011,2012"))
         (("name" . "psltscale") ("ver" . "2009,2010,2011,2012,2013LT,2013,2014,2015,2016,2017"))
         (("name" . "psolheight") ("ver" . "2009,2010,2011,2012,2013,2014,2015,2016,2017"))
         (("name" . "psolwidth") ("ver" . "2009,2010,2011,2012,2013,2014,2015,2016,2017"))
         (("name" . "psprolog") ("ver" . "2009,2010,2011,2012,2013LT,2013,2014,2015,2016,2017"))
         (("name" . "psquality") ("ver" . "2009,2010,2011,2012,2013,2014,2015,2016,2017"))
         (("name" . "pstylemode") ("ver" . "2009,2010,2011,2012,2013LT,2013,2014,2015,2016,2017"))
         (("name" . "pstylepolicy") ("ver" . "2009,2010,2011,2012,2013LT,2013,2014,2015,2016,2017"))
         (("name" . "psvpscale") ("ver" . "2009,2010,2011,2012,2013,2014,2015,2016,2017"))
         (("name" . "publishallsheets") ("ver" . "2009,2010,2011,2012,2013LT,2013,2014,2015,2016,2017"))
         (("name" . "publishcollate") ("ver" . "2009,2010,2011,2012,2013LT,2013,2014,2015,2016,2017"))
         (("name" . "publishhatch") ("ver" . "2009,2010,2011,2012,2013LT,2013,2014,2015,2016,2017"))
         (("name" . "pucsbase") ("ver" . "2009,2010,2011,2012,2013LT,2013,2014,2015,2016,2017"))
         (("name" . "qaflags") ("ver" . "2009,2010,2011,2012,2013,2014,2015,2016,2017"))
         (("name" . "qaucslock") ("ver" . "2009,2010,2011,2012,2013,2014,2015,2016,2017"))
         (("name" . "qcstate") ("ver" . "2009,2010,2011,2012,2013,2014,2015,2016,2017"))
         (("name" . "qplocation") ("ver" . "2009,2010,2011,2012,2013LT,2013,2014,2015,2016,2017"))
         (("name" . "qpmode") ("ver" . "2009,2010,2011,2012,2013LT,2013,2014,2015,2016,2017"))
         (("name" . "qtextmode") ("ver" . "2009,2010,2011,2012,2013LT,2013,2014,2015,2016,2017"))
         (("name" . "queuedregenmax") ("ver" . "2009,2010,2011,2012,2013,2014,2015,2016,2017"))
         (("name" . "qvdrawingpin") ("ver" . "2009,2010,2011,2012,2013LT,2013,2014,2015,2016,2017"))
         (("name" . "qvlayoutpin") ("ver" . "2009,2010,2011,2012,2013LT,2013,2014,2015,2016,2017"))
         (("name" . "r14rasterplot") ("ver" . "2009,2010,2011,2012,2013,2014,2015,2016,2017"))
         (("name" . "rasterdpi") ("ver" . "2009,2010,2011,2012,2013LT,2013,2014,2015,2016,2017"))
         (("name" . "rasterpercent") ("ver" . "2009,2010,2011,2012,2013LT,2013,2014,2015,2016,2017"))
         (("name" . "rasterpreview") ("ver" . "2009,2010,2011,2012,2013,2014,2015,2016"))
         (("name" . "rasterthreshold") ("ver" . "2009,2010,2011,2012,2013LT,2013,2014,2015,2016,2017"))
         (("name" . "re-init") ("ver" . "2009,2010,2011,2012,2013,2014,2015,2016,2017"))
         (("name" . "rebuild2dcv") ("ver" . "2011,2012,2013,2014,2015,2016,2017"))
         (("name" . "rebuild2ddegree") ("ver" . "2011,2012,2013,2014,2015,2016,2017"))
         (("name" . "rebuild2doption") ("ver" . "2011,2012,2013,2014,2015,2016,2017"))
         (("name" . "rebuilddegreeu") ("ver" . "2011,2012,2013,2014,2015,2016,2017"))
         (("name" . "rebuilddegreev") ("ver" . "2011,2012,2013,2014,2015,2016,2017"))
         (("name" . "rebuildoptions") ("ver" . "2011,2012,2013,2014,2015,2016,2017"))
         (("name" . "rebuildu") ("ver" . "2011,2012,2013,2014,2015,2016,2017"))
         (("name" . "rebuildv") ("ver" . "2011,2012,2013,2014,2015,2016,2017"))
         (("name" . "recoverauto") ("ver" . "2011,2012,2013LT,2013,2014,2015,2016,2017"))
         (("name" . "recoverymode") ("ver" . "2009,2010,2011,2012,2013LT,2013,2014,2015,2016,2017"))
         (("name" . "refeditname") ("ver" . "2009,2010,2011,2012,2013LT,2013,2014,2015,2016,2017"))
         (("name" . "regenmode") ("ver" . "2009,2010,2011,2012,2013LT,2013,2014,2015,2016,2017"))
         (("name" . "rememberfolders") ("ver" . "2009,2010,2011,2012,2013LT,2013,2014,2015,2016,2017"))
         (("name" . "renderlevel") ("ver" . "2016,2017"))
         (("name" . "renderlightcalc") ("ver" . "2016,2017"))
         (("name" . "renderprefsstate") ("ver" . "2009,2010,2011,2012,2013,2014,2015,2016,2017"))
         (("name" . "renderquality") ("ver" . "2009,2010,2011,2012,2013,2014,2015,2016"))
         (("name" . "rendertarget") ("ver" . "2016,2017"))
         (("name" . "rendertime") ("ver" . "2016,2017"))
         (("name" . "renderuserlights") ("ver" . "2009,2010,2011,2012,2013,2014,2015,2016,2017"))
         (("name" . "reporterror") ("ver" . "2009,2010,2011,2012,2013LT,2013,2014,2015,2016,2017"))
         (("name" . "revcloudcreatemode") ("ver" . "2016,2017"))
         (("name" . "revcloudgrips") ("ver" . "2016,2017"))
         (("name" . "ribbonbgload") ("ver" . "2012,2013LT,2013,2014,2015,2016,2017"))
         (("name" . "ribboncontextselect") ("ver" . "2010,2011,2012,2013LT,2013,2014"))
         (("name" . "ribboncontextsellim") ("ver" . "2010,2011,2012,2013LT,2013,2014,2015,2016,2017"))
         (("name" . "ribbondockedheight") ("ver" . "2010,2011,2012,2013LT,2013,2014,2015,2016,2017"))
         (("name" . "ribboniconresize") ("ver" . "2012,2013LT,2013,2014,2015,2016,2017"))
         (("name" . "ribbonselectmode") ("ver" . "2010,2011,2012,2013LT,2013,2014,2015,2016,2017"))
         (("name" . "ribbonstate") ("ver" . "2009,2010,2011,2012,2013LT,2013,2014,2015,2016,2017"))
         (("name" . "roamablerootprefix") ("ver" . "2009,2010,2011,2012,2013LT,2013,2014,2015,2016,2017"))
         (("name" . "rolloveropacity") ("ver" . "2011,2012,2013,2014,2015,2016,2017"))
         (("name" . "rollovertips") ("ver" . "2009,2010,2011,2012,2013LT,2013,2014,2015,2016,2017"))
         (("name" . "rtdisplay") ("ver" . "2009,2010,2011,2012,2013LT,2013,2014,2015,2016,2017"))
         (("name" . "safemode") ("ver" . "2014,2015,2016,2017"))
         (("name" . "savefidelity") ("ver" . "2009,2010,2011,2012,2013LT,2013,2014,2015,2016,2017"))
         (("name" . "savefile") ("ver" . "2009,2010,2011,2012,2013LT,2013,2014,2015,2016,2017"))
         (("name" . "savefilepath") ("ver" . "2009,2010,2011,2012,2013LT,2013,2014,2015,2016,2017"))
         (("name" . "savename") ("ver" . "2009,2010,2011,2012,2013LT,2013,2014,2015,2016,2017"))
         (("name" . "savetime") ("ver" . "2009,2010,2011,2012,2013LT,2013,2014,2015,2016,2017"))
         (("name" . "screenboxes") ("ver" . "2009,2010,2011,2012,2013,2014,2015,2016,2017"))
         (("name" . "screenmenu") ("ver" . "2011,2017"))
         (("name" . "screenmode") ("ver" . "2009,2010,2011,2012,2013,2014,2015,2016,2017"))
         (("name" . "screensize") ("ver" . "2009,2010,2011,2012,2013LT,2013,2014,2015,2016,2017"))
         (("name" . "sdi") ("ver" . "2009,2010,2011,2012,2013,2014,2015,2016,2017"))
         (("name" . "sectionoffsetinc") ("ver" . "2016,2017"))
         (("name" . "sectionthicknessinc") ("ver" . "2016,2017"))
         (("name" . "secureload") ("ver" . "2014,2015,2016,2017"))
         (("name" . "selectionannodisplay") ("ver" . "2009,2010,2011,2012,2013LT,2013,2014,2015,2016,2017"))
         (("name" . "selectionarea") ("ver" . "2009,2010,2011,2012,2013LT,2013,2014,2015,2016,2017"))
         (("name" . "selectionareaopacity") ("ver" . "2009,2010,2011,2012,2013LT,2013,2014,2015,2016,2017"))
         (("name" . "selectioncycling") ("ver" . "2011,2012,2013LT,2013,2014,2015,2016,2017"))
         (("name" . "selectioneffect") ("ver" . "2015,2016,2017"))
         (("name" . "selectioneffectcolor") ("ver" . "2016,2017"))
         (("name" . "selectionoffscreen") ("ver" . "2017"))
         (("name" . "selectionpreview") ("ver" . "2009,2010,2011,2012,2013LT,2013,2014,2015,2016,2017"))
         (("name" . "selectionpreviewlimit") ("ver" . "2013LT,2013,2014,2015,2016,2017"))
         (("name" . "selectlastmode") ("ver" . "2009,2010,2011,2012,2013,2014,2015,2016,2017"))
         (("name" . "selectsimilarmode") ("ver" . "2011,2012,2013LT,2013,2014,2015,2016,2017"))
         (("name" . "setbylayermode") ("ver" . "2009,2010,2011,2012,2013LT,2013,2014,2015,2016,2017"))
         (("name" . "shadedge") ("ver" . "2009,2010,2011,2012,2013LT,2013,2014,2015,2016,2017"))
         (("name" . "shadedif") ("ver" . "2009,2010,2011,2012,2013LT,2013,2014,2015,2016,2017"))
         (("name" . "shadowplanelocation") ("ver" . "2009,2010,2011,2012,2013,2014,2015,2016,2017"))
         (("name" . "shortcutmenu") ("ver" . "2009,2010,2011,2012,2013LT,2013,2014,2015,2016,2017"))
         (("name" . "shortcutmenuduration") ("ver" . "2012,2013LT,2013,2014,2015,2016,2017"))
         (("name" . "showhist") ("ver" . "2009,2010,2011,2012,2013,2014,2015,2016,2017"))
         (("name" . "showlayerusage") ("ver" . "2009,2010,2011,2012,2013LT,2013,2014,2015,2016,2017"))
         (("name" . "showmotionpin") ("ver" . "2009,2010,2011,2012,2013,2014,2015,2016,2017"))
         (("name" . "showpagesetupfornewlayouts") ("ver" . "2012,2013LT,2013,2014,2015,2016,2017"))
         (("name" . "shpname") ("ver" . "2009,2010,2011,2012,2013,2014,2015,2016,2017"))
         (("name" . "sigwarn") ("ver" . "2009,2010,2011,2012,2013LT,2013,2014,2015,2016,2017"))
         (("name" . "sketchinc") ("ver" . "2009,2010,2011,2012,2013LT,2013,2014,2015,2016,2017"))
         (("name" . "skip2dregens") ("ver" . "2009,2010,2011,2012,2013,2014,2015,2016,2017"))
         (("name" . "skpoly") ("ver" . "2009,2010,2011,2012,2013LT,2013,2014,2015,2016,2017"))
         (("name" . "sktolerance") ("ver" . "2011,2012,2013LT,2013,2014,2015,2016,2017"))
         (("name" . "skystatus") ("ver" . "2009,2010,2011,2012,2013,2014,2015,2016,2017"))
         (("name" . "smoothmeshconvert") ("ver" . "2010,2011,2012,2013,2014,2015,2016,2017"))
         (("name" . "smoothmeshgrid") ("ver" . "2010,2011,2012,2013,2014,2015,2016,2017"))
         (("name" . "smoothmeshmaxface") ("ver" . "2010,2011,2012,2013,2014,2015,2016,2017"))
         (("name" . "smoothmeshmaxlev") ("ver" . "2010,2011,2012,2013,2014,2015,2016,2017"))
         (("name" . "smstate") ("ver" . "2011,2012,2013,2014,2015,2016,2017"))
         (("name" . "snapang") ("ver" . "2009,2010,2011,2012,2013LT,2013,2014,2015,2016,2017"))
         (("name" . "snapbase") ("ver" . "2009,2010,2011,2012,2013LT,2013,2014,2015,2016,2017"))
         (("name" . "snapgridlegacy") ("ver" . "2012,2013,2014,2015,2016,2017"))
         (("name" . "snapisopair") ("ver" . "2009,2010,2011,2012,2013LT,2013,2014,2015,2016,2017"))
         (("name" . "snapmode") ("ver" . "2009,2010,2011,2012,2013LT,2013,2014,2015,2016,2017"))
         (("name" . "snapstyl") ("ver" . "2009,2010,2011,2012,2013LT,2013,2014,2015,2016,2017"))
         (("name" . "snaptype") ("ver" . "2009,2010,2011,2012,2013LT,2013,2014,2015,2016,2017"))
         (("name" . "snapunit") ("ver" . "2009,2010,2011,2012,2013LT,2013,2014,2015,2016,2017"))
         (("name" . "solidcheck") ("ver" . "2009,2010,2011,2012,2013,2014,2015,2016,2017"))
         (("name" . "solidhist") ("ver" . "2009,2010,2011,2012,2013,2014,2015,2016,2017"))
         (("name" . "sortents") ("ver" . "2009,2010,2011,2012,2013LT,2013,2014,2015,2016,2017"))
         (("name" . "sortorder") ("ver" . "2015,2016,2017"))
         (("name" . "spaceswitch") ("ver" . "2009,2010,2011,2012,2013,2014,2015,2016,2017"))
         (("name" . "spldegree") ("ver" . "2011,2012,2013LT,2013,2014,2015,2016,2017"))
         (("name" . "splframe") ("ver" . "2009,2010,2011,2012,2013LT,2013,2014,2015,2016,2017"))
         (("name" . "splinesegs") ("ver" . "2009,2010,2011,2012,2013LT,2013,2014,2015,2016,2017"))
         (("name" . "splinetype") ("ver" . "2009,2010,2011,2012,2013LT,2013,2014,2015,2016,2017"))
         (("name" . "splknots") ("ver" . "2011,2012,2013LT,2013,2014,2015,2016,2017"))
         (("name" . "splmethod") ("ver" . "2011,2012,2013LT,2013,2014,2015,2016,2017"))
         (("name" . "splperiodic") ("ver" . "2012,2013LT,2013,2014,2015,2016,2017"))
         (("name" . "ssfound") ("ver" . "2009,2010,2011,2012,2013LT,2013,2014,2015,2016,2017"))
         (("name" . "sslocate") ("ver" . "2009,2010,2011,2012,2013LT,2013,2014,2015,2016,2017"))
         (("name" . "ssmautoopen") ("ver" . "2009,2010,2011,2012,2013LT,2013,2014,2015,2016,2017"))
         (("name" . "ssmopenrefresh") ("ver" . "2009,2010,2011,2012,2013,2014,2015,2016"))
         (("name" . "ssmpolltime") ("ver" . "2009,2010,2011,2012,2013LT,2013,2014,2015,2016,2017"))
         (("name" . "ssmsheetstatus") ("ver" . "2009,2010,2011,2012,2013LT,2013,2014,2015,2016,2017"))
         (("name" . "ssmstate") ("ver" . "2009,2010,2011,2012,2013,2014,2015,2016,2017"))
         (("name" . "standardsviolation") ("ver" . "2009,2010,2011,2012,2013,2014,2015,2016,2017"))
         (("name" . "startinfolder") ("ver" . "2013,2014,2015,2016,2017"))
         (("name" . "startmode") ("ver" . "2016,2017"))
         (("name" . "startup") ("ver" . "2009,2010,2011,2012,2013LT,2013,2014,2015,2016,2017"))
         (("name" . "statusbar") ("ver" . "2009,2010,2011,2012,2013LT,2013,2014,2015,2016,2017"))
         (("name" . "stepsize") ("ver" . "2009,2010,2011,2012,2013,2014,2015,2016,2017"))
         (("name" . "stepspersec") ("ver" . "2009,2010,2011,2012,2013,2014,2015,2016,2017"))
         (("name" . "stylesheet") ("ver" . "2009,2010,2011,2012,2013,2014,2015,2016"))
         (("name" . "subobjselectionmode") ("ver" . "2010,2011,2012,2013,2014,2015,2016,2017"))
         (("name" . "sunpropertiesstate") ("ver" . "2009,2010,2011,2012,2013,2014,2015,2016,2017"))
         (("name" . "sunstatus") ("ver" . "2009,2010,2011,2012,2013,2014,2015,2016,2017"))
         (("name" . "suppressalerts") ("ver" . "2013LT,2013,2014,2015,2016,2017"))
         (("name" . "surfaceassociativity") ("ver" . "2011,2012,2013,2014,2015,2016,2017"))
         (("name" . "surfaceassociativitydrag") ("ver" . "2011,2012,2013,2014,2015,2016,2017"))
         (("name" . "surfaceautotrim") ("ver" . "2011,2012,2013,2014,2015,2016,2017"))
         (("name" . "surfacemodelingmode") ("ver" . "2011,2012,2013,2014,2015,2016,2017"))
         (("name" . "surfoffsetconnect") ("ver" . "2011,2012,2013,2014,2015,2016,2017"))
         (("name" . "surftab1") ("ver" . "2009,2010,2011,2012,2013,2014,2015,2016,2017"))
         (("name" . "surftab2") ("ver" . "2009,2010,2011,2012,2013,2014,2015,2016,2017"))
         (("name" . "surftrimautoextend") ("ver" . "2011,2012,2013,2014,2015,2016,2017"))
         (("name" . "surftrimprojection") ("ver" . "2011,2012,2013,2014,2015,2016,2017"))
         (("name" . "surftype") ("ver" . "2009,2010,2011,2012,2013,2014,2015,2016,2017"))
         (("name" . "surfu") ("ver" . "2009,2010,2011,2012,2013,2014,2015,2016,2017"))
         (("name" . "surfv") ("ver" . "2009,2010,2011,2012,2013,2014,2015,2016,2017"))
         (("name" . "syscodepage") ("ver" . "2009,2010,2011,2012,2013LT,2013,2014,2015,2016,2017"))
         (("name" . "sysmon") ("ver" . "2016,2017"))
         (("name" . "tableindicator") ("ver" . "2009,2010,2011,2012,2013LT,2013,2014,2015,2016,2017"))
         (("name" . "tabletoolbar") ("ver" . "2009,2010,2011,2012,2013LT,2013,2014,2015,2016,2017"))
         (("name" . "tabmode") ("ver" . "2009,2010,2011,2012,2013LT,2013,2014,2015,2016,2017"))
         (("name" . "target") ("ver" . "2009,2010,2011,2012,2013LT,2013,2014,2015,2016,2017"))
         (("name" . "tbcustomize") ("ver" . "2009,2010,2011,2012,2013,2014,2015,2016,2017"))
         (("name" . "tbshowshortcuts") ("ver" . "2012,2013LT,2013,2014,2015,2016,2017"))
         (("name" . "tdcreate") ("ver" . "2009,2010,2011,2012,2013LT,2013,2014,2015,2016,2017"))
         (("name" . "tdindwg") ("ver" . "2009,2010,2011,2012,2013LT,2013,2014,2015,2016,2017"))
         (("name" . "tducreate") ("ver" . "2009,2010,2011,2012,2013LT,2013,2014,2015,2016,2017"))
         (("name" . "tdupdate") ("ver" . "2009,2010,2011,2012,2013LT,2013,2014,2015,2016,2017"))
         (("name" . "tdusrtimer") ("ver" . "2009,2010,2011,2012,2013LT,2013,2014,2015,2016,2017"))
         (("name" . "tduupdate") ("ver" . "2009,2010,2011,2012,2013LT,2013,2014,2015,2016,2017"))
         (("name" . "tempoverrides") ("ver" . "2009,2010,2011,2012,2013LT,2013,2014,2015,2016,2017"))
         (("name" . "tempprefix") ("ver" . "2009,2010,2011,2012,2013,2014,2015,2016,2017"))
         (("name" . "textalignmode") ("ver" . "2015,2016,2017"))
         (("name" . "textalignspacing") ("ver" . "2015,2016,2017"))
         (("name" . "textallcaps") ("ver" . "2015,2016,2017"))
         (("name" . "textautocorrectcaps") ("ver" . "2015,2016,2017"))
         (("name" . "texted") ("ver" . "2011,2012,2013LT,2013,2014,2015,2016,2017"))
         (("name" . "texteditmode") ("ver" . "2017"))
         (("name" . "texteditor") ("ver" . "2010,2011,2012,2013,2014,2015,2016,2017"))
         (("name" . "texteval") ("ver" . "2009,2010,2011,2012,2013LT,2013,2014,2015,2016,2017"))
         (("name" . "textfill") ("ver" . "2009,2010,2011,2012,2013LT,2013,2014,2015,2016,2017"))
         (("name" . "textjustify") ("ver" . "2014,2015,2016,2017"))
         (("name" . "textoutputfileformat") ("ver" . "2009,2010,2011,2012,2013,2014,2015,2016,2017"))
         (("name" . "textqlty") ("ver" . "2009,2010,2011,2012,2013LT,2013,2014,2015,2016,2017"))
         (("name" . "textsize") ("ver" . "2009,2010,2011,2012,2013LT,2013,2014,2015,2016,2017"))
         (("name" . "textstyle") ("ver" . "2009,2010,2011,2012,2013LT,2013,2014,2015,2016,2017"))
         (("name" . "thickness") ("ver" . "2009,2010,2011,2012,2013LT,2013,2014,2015,2016,2017"))
         (("name" . "thumbsave") ("ver" . "2013LT,2013,2014,2015,2016,2017"))
         (("name" . "thumbsize") ("ver" . "2009,2010,2011,2012,2013,2014,2015,2016,2017"))
         (("name" . "tilemode") ("ver" . "2009,2010,2011,2012,2013LT,2013,2014,2015,2016,2017"))
         (("name" . "timezone") ("ver" . "2009,2010,2011,2012,2013LT,2013,2014,2015,2016,2017"))
         (("name" . "tooltipmerge") ("ver" . "2009,2010,2011,2012,2013LT,2013,2014,2015,2016,2017"))
         (("name" . "tooltips") ("ver" . "2009,2010,2011,2012,2013LT,2013,2014,2015,2016,2017"))
         (("name" . "tooltipsize") ("ver" . "2012,2013LT,2013,2014,2015,2016,2017"))
         (("name" . "tooltiptransparency") ("ver" . "2012,2013LT,2013,2014,2015,2016,2017"))
         (("name" . "touchmode") ("ver" . "2014,2015,2016,2017"))
         (("name" . "tpstate") ("ver" . "2009,2010,2011,2012,2013,2014,2015,2016,2017"))
         (("name" . "tracewid") ("ver" . "2009,2010,2011,2012,2013,2014,2015,2016,2017"))
         (("name" . "trackpath") ("ver" . "2009,2010,2011,2012,2013LT,2013,2014,2015,2016,2017"))
         (("name" . "transparencydisplay") ("ver" . "2011,2012,2013,2014,2015,2016,2017"))
         (("name" . "trayicons") ("ver" . "2009,2010,2011,2012,2013LT,2013,2014,2015,2016,2017"))
         (("name" . "traynotify") ("ver" . "2009,2010,2011,2012,2013LT,2013,2014,2015,2016,2017"))
         (("name" . "traytimeout") ("ver" . "2009,2010,2011,2012,2013LT,2013,2014,2015,2016,2017"))
         (("name" . "treedepth") ("ver" . "2009,2010,2011,2012,2013LT,2013,2014,2015,2016,2017"))
         (("name" . "treemax") ("ver" . "2009,2010,2011,2012,2013LT,2013,2014,2015,2016,2017"))
         (("name" . "trimmode") ("ver" . "2009,2010,2011,2012,2013LT,2013,2014,2015,2016,2017"))
         (("name" . "trusteddomains") ("ver" . "2014,2015,2016,2017"))
         (("name" . "trustedpaths") ("ver" . "2014,2015,2016,2017"))
         (("name" . "tspacefac") ("ver" . "2009,2010,2011,2012,2013LT,2013,2014,2015,2016,2017"))
         (("name" . "tspacetype") ("ver" . "2009,2010,2011,2012,2013LT,2013,2014,2015,2016,2017"))
         (("name" . "tstackalign") ("ver" . "2009,2010,2011,2012,2013LT,2013,2014,2015,2016,2017"))
         (("name" . "tstacksize") ("ver" . "2009,2010,2011,2012,2013LT,2013,2014,2015,2016,2017"))
         (("name" . "ucs2ddisplaysetting") ("ver" . "2012,2013LT,2013,2014,2015,2016,2017"))
         (("name" . "ucs3dparadisplaysetting") ("ver" . "2012,2013,2014,2015,2016,2017"))
         (("name" . "ucs3dperpdisplaysetting") ("ver" . "2012,2013,2014,2015,2016,2017"))
         (("name" . "ucsaxisang") ("ver" . "2009,2010,2011,2012,2013LT,2013,2014,2015,2016,2017"))
         (("name" . "ucsbase") ("ver" . "2009,2010,2011,2012,2013LT,2013,2014,2015,2016,2017"))
         (("name" . "ucsdetect") ("ver" . "2009,2010,2011,2012,2013,2014,2015,2016,2017"))
         (("name" . "ucsfollow") ("ver" . "2009,2010,2011,2012,2013LT,2013,2014,2015,2016,2017"))
         (("name" . "ucsicon") ("ver" . "2009,2010,2011,2012,2013LT,2013,2014,2015,2016,2017"))
         (("name" . "ucsname") ("ver" . "2009,2010,2011,2012,2013LT,2013,2014,2015,2016,2017"))
         (("name" . "ucsorg") ("ver" . "2009,2010,2011,2012,2013LT,2013,2014,2015,2016,2017"))
         (("name" . "ucsortho") ("ver" . "2009,2010,2011,2012,2013LT,2013,2014,2015,2016,2017"))
         (("name" . "ucsselectmode") ("ver" . "2012,2013LT,2013,2014,2015,2016,2017"))
         (("name" . "ucsview") ("ver" . "2009,2010,2011,2012,2013LT,2013,2014,2015,2016,2017"))
         (("name" . "ucsvp") ("ver" . "2009,2010,2011,2012,2013,2014,2015,2016,2017"))
         (("name" . "ucsxdir") ("ver" . "2009,2010,2011,2012,2013LT,2013,2014,2015,2016,2017"))
         (("name" . "ucsydir") ("ver" . "2009,2010,2011,2012,2013LT,2013,2014,2015,2016,2017"))
         (("name" . "undoctl") ("ver" . "2009,2010,2011,2012,2013LT,2013,2014,2015,2016,2017"))
         (("name" . "undomarks") ("ver" . "2009,2010,2011,2012,2013LT,2013,2014,2015,2016,2017"))
         (("name" . "unitmode") ("ver" . "2009,2010,2011,2012,2013LT,2013,2014,2015,2016,2017"))
         (("name" . "uosnap") ("ver" . "2010,2011,2012,2013LT,2013,2014,2015,2016,2017"))
         (("name" . "updatethumbnail") ("ver" . "2009,2010,2011,2012,2013LT,2013,2014,2015,2016,2017"))
         (("name" . "useacis") ("ver" . "2009,2010,2011,2012,2013,2014"))
         (("name" . "useri1") ("ver" . "2009,2010,2011,2012,2013,2014,2015,2016,2017"))
         (("name" . "useri2") ("ver" . "2009,2010,2011,2012,2013,2014,2015,2016,2017"))
         (("name" . "useri3") ("ver" . "2009,2010,2011,2012,2013,2014,2015,2016,2017"))
         (("name" . "useri4") ("ver" . "2009,2010,2011,2012,2013,2014,2015,2016,2017"))
         (("name" . "useri5") ("ver" . "2009,2010,2011,2012,2013,2014,2015,2016,2017"))
         (("name" . "username") ("ver" . "2013LT"))
         (("name" . "userr1") ("ver" . "2009,2010,2011,2012,2013,2014,2015,2016,2017"))
         (("name" . "userr2") ("ver" . "2009,2010,2011,2012,2013,2014,2015,2016,2017"))
         (("name" . "userr3") ("ver" . "2009,2010,2011,2012,2013,2014,2015,2016,2017"))
         (("name" . "userr4") ("ver" . "2009,2010,2011,2012,2013,2014,2015,2016,2017"))
         (("name" . "userr5") ("ver" . "2009,2010,2011,2012,2013,2014,2015,2016,2017"))
         (("name" . "users1") ("ver" . "2009,2010,2011,2012,2013,2014,2015,2016,2017"))
         (("name" . "users2") ("ver" . "2009,2010,2011,2012,2013,2014,2015,2016,2017"))
         (("name" . "users3") ("ver" . "2009,2010,2011,2012,2013,2014,2015,2016,2017"))
         (("name" . "users4") ("ver" . "2009,2010,2011,2012,2013,2014,2015,2016,2017"))
         (("name" . "users5") ("ver" . "2009,2010,2011,2012,2013,2014,2015,2016,2017"))
         (("name" . "version") ("ver" . "2013LT"))
         (("name" . "viewbackstatus") ("ver" . "2012,2013LT,2013,2014,2015,2016,2017"))
         (("name" . "viewcreation") ("ver" . "2012,2013,2014,2015,2016,2017"))
         (("name" . "viewctr") ("ver" . "2009,2010,2011,2012,2013LT,2013,2014,2015,2016,2017"))
         (("name" . "viewdetailcreation") ("ver" . "2013,2014,2015,2016,2017"))
         (("name" . "viewdetaileditor") ("ver" . "2013,2014,2015,2016,2017"))
         (("name" . "viewdir") ("ver" . "2009,2010,2011,2012,2013LT,2013,2014,2015,2016,2017"))
         (("name" . "vieweditor") ("ver" . "2012,2013,2014,2015,2016,2017"))
         (("name" . "viewfwdstatus") ("ver" . "2012,2013LT,2013,2014,2015,2016,2017"))
         (("name" . "viewmode") ("ver" . "2009,2010,2011,2012,2013LT,2013,2014,2015,2016,2017"))
         (("name" . "viewsectioncreation") ("ver" . "2013,2014,2015,2016,2017"))
         (("name" . "viewsectioneditor") ("ver" . "2013,2014,2015,2016,2017"))
         (("name" . "viewsize") ("ver" . "2009,2010,2011,2012,2013LT,2013,2014,2015,2016,2017"))
         (("name" . "viewsketchmode") ("ver" . "2013,2014,2015,2016,2017"))
         (("name" . "viewtwist") ("ver" . "2009,2010,2011,2012,2013LT,2013,2014,2015,2016,2017"))
         (("name" . "viewupdateauto") ("ver" . "2013,2014,2015,2016,2017"))
         (("name" . "visretain") ("ver" . "2009,2010,2011,2012,2013LT,2013,2014,2015,2016,2017"))
         (("name" . "vpcontrol") ("ver" . "2012,2013,2014,2015,2016,2017"))
         (("name" . "vplayeroverrides") ("ver" . "2009,2010,2011,2012,2013LT,2013,2014,2015,2016,2017"))
         (("name" . "vplayeroverridesmode") ("ver" . "2009,2010,2011,2012,2013LT,2013,2014,2015,2016,2017"))
         (("name" . "vpmaximizedstate") ("ver" . "2009,2010,2011,2012,2013LT,2013,2014,2015,2016,2017"))
         (("name" . "vprotateassoc") ("ver" . "2009,2010,2011,2012,2013LT,2013,2014,2015,2016,2017"))
         (("name" . "vsacurvaturehigh") ("ver" . "2011,2012,2013,2014,2015,2016,2017"))
         (("name" . "vsacurvaturelow") ("ver" . "2011,2012,2013,2014,2015,2016,2017"))
         (("name" . "vsacurvaturetype") ("ver" . "2011,2012,2013,2014,2015,2016,2017"))
         (("name" . "vsadraftanglehigh") ("ver" . "2011,2012,2013,2014,2015,2016,2017"))
         (("name" . "vsadraftanglelow") ("ver" . "2011,2012,2013,2014,2015,2016,2017"))
         (("name" . "vsazebracolor1") ("ver" . "2011,2012,2013,2014,2015,2016,2017"))
         (("name" . "vsazebracolor2") ("ver" . "2011,2012,2013,2014,2015,2016,2017"))
         (("name" . "vsazebradirection") ("ver" . "2011,2012,2013,2014,2015,2016,2017"))
         (("name" . "vsazebrasize") ("ver" . "2011,2012,2013,2014,2015,2016,2017"))
         (("name" . "vsazebratype") ("ver" . "2011,2012,2013,2014,2015,2016,2017"))
         (("name" . "vsbackgrounds") ("ver" . "2009,2010,2011,2012,2013,2014,2015,2016,2017"))
         (("name" . "vsedgecolor") ("ver" . "2009,2010,2011,2012,2013,2014,2015,2016,2017"))
         (("name" . "vsedgejitter") ("ver" . "2009,2010,2011,2012,2013,2014,2015,2016,2017"))
         (("name" . "vsedgelex") ("ver" . "2011,2012,2013,2014,2015,2016,2017"))
         (("name" . "vsedgeoverhang") ("ver" . "2009,2010,2011,2012,2013,2014,2015,2016,2017"))
         (("name" . "vsedges") ("ver" . "2009,2010,2011,2012,2013,2014,2015,2016,2017"))
         (("name" . "vsedgesmooth") ("ver" . "2009,2010,2011,2012,2013,2014,2015,2016,2017"))
         (("name" . "vsfacecolormode") ("ver" . "2009,2010,2011,2012,2013,2014,2015,2016,2017"))
         (("name" . "vsfacehighlight") ("ver" . "2009,2010,2011,2012,2013,2014,2015,2016,2017"))
         (("name" . "vsfaceopacity") ("ver" . "2009,2010,2011,2012,2013,2014,2015,2016,2017"))
         (("name" . "vsfacestyle") ("ver" . "2009,2010,2011,2012,2013,2014,2015,2016,2017"))
         (("name" . "vshalogap") ("ver" . "2009,2010,2011,2012,2013,2014,2015,2016,2017"))
         (("name" . "vshideprecision") ("ver" . "2009,2010,2011,2012,2013,2014,2015,2016,2017"))
         (("name" . "vsintersectioncolor") ("ver" . "2009,2010,2011,2012,2013,2014,2015,2016,2017"))
         (("name" . "vsintersectionedges") ("ver" . "2009,2010,2011,2012,2013,2014,2015,2016,2017"))
         (("name" . "vsintersectionltype") ("ver" . "2009,2010,2011,2012,2013,2014,2015,2016,2017"))
         (("name" . "vsisoontop") ("ver" . "2009,2010,2011,2012,2013,2014,2015,2016,2017"))
         (("name" . "vslightingquality") ("ver" . "2009,2010,2011,2012,2013,2014,2015,2016,2017"))
         (("name" . "vsmaterialmode") ("ver" . "2009,2010,2011,2012,2013,2014,2015,2016,2017"))
         (("name" . "vsmax") ("ver" . "2009,2010,2011,2012,2013LT,2013,2014,2015,2016,2017"))
         (("name" . "vsmin") ("ver" . "2009,2010,2011,2012,2013LT,2013,2014,2015,2016,2017"))
         (("name" . "vsmonocolor") ("ver" . "2009,2010,2011,2012,2013,2014,2015,2016,2017"))
         (("name" . "vsobscuredcolor") ("ver" . "2009,2010,2011,2012,2013,2014,2015,2016,2017"))
         (("name" . "vsobscurededges") ("ver" . "2009,2010,2011,2012,2013,2014,2015,2016,2017"))
         (("name" . "vsobscuredltype") ("ver" . "2009,2010,2011,2012,2013,2014,2015,2016,2017"))
         (("name" . "vsoccludedcolor") ("ver" . "2011,2012,2013,2014,2015,2016,2017"))
         (("name" . "vsoccludededges") ("ver" . "2011,2012,2013,2014,2015,2016,2017"))
         (("name" . "vsoccludedltype") ("ver" . "2011,2012,2013,2014,2015,2016,2017"))
         (("name" . "vsshadows") ("ver" . "2009,2010,2011,2012,2013,2014,2015,2016,2017"))
         (("name" . "vssilhedges") ("ver" . "2009,2010,2011,2012,2013,2014,2015,2016,2017"))
         (("name" . "vssilhwidth") ("ver" . "2009,2010,2011,2012,2013,2014,2015,2016,2017"))
         (("name" . "vsstate") ("ver" . "2009,2010,2011,2012,2013,2014,2015,2016,2017"))
         (("name" . "vtduration") ("ver" . "2009,2010,2011,2012,2013LT,2013,2014,2015,2016,2017"))
         (("name" . "vtenable") ("ver" . "2009,2010,2011,2012,2013LT,2013,2014,2015,2016,2017"))
         (("name" . "vtfps") ("ver" . "2009,2010,2011,2012,2013LT,2013,2014,2015,2016,2017"))
         (("name" . "vtoolmotion") ("ver" . "2016,2017"))
         (("name" . "wbdefaultbrowser") ("ver" . "2011,2012,2013LT,2013,2014,2015,2016,2017"))
         (("name" . "wbhelponline") ("ver" . "2011,2012,2013LT,2013,2014,2015,2016,2017"))
         (("name" . "wbhelptype") ("ver" . "2011,2012,2013LT,2013,2014,2015,2016,2017"))
         (("name" . "whiparc") ("ver" . "2009,2010,2011,2012,2013LT,2013,2014,2015,2016,2017"))
         (("name" . "whipthread") ("ver" . "2009,2010,2011,2012,2013,2014,2015,2016,2017"))
         (("name" . "windowareacolor") ("ver" . "2009,2010,2011,2012,2013LT,2013,2014,2015,2016,2017"))
         (("name" . "wipeoutframe") ("ver" . "2013LT,2013,2014,2015,2016,2017"))
         (("name" . "wmfbkgnd") ("ver" . "2009,2010,2011,2012,2013LT,2013,2014,2015,2016,2017"))
         (("name" . "wmfforegnd") ("ver" . "2009,2010,2011,2012,2013LT,2013,2014,2015,2016,2017"))
         (("name" . "workingfolder") ("ver" . "2016,2017"))
         (("name" . "workspacelabel") ("ver" . "2012,2013LT,2013,2014,2015,2016,2017"))
         (("name" . "worlducs") ("ver" . "2009,2010,2011,2012,2013LT,2013,2014,2015,2016,2017"))
         (("name" . "worldview") ("ver" . "2009,2010,2011,2012,2013LT,2013,2014,2015,2016,2017"))
         (("name" . "writestat") ("ver" . "2009,2010,2011,2012,2013,2014,2015,2016,2017"))
         (("name" . "wsautosave") ("ver" . "2011,2012,2013,2014,2015,2016,2017"))
         (("name" . "wscurrent") ("ver" . "2009,2010,2011,2012,2013LT,2013,2014,2015,2016,2017"))
         (("name" . "xclipframe") ("ver" . "2009,2010,2011,2012,2013LT,2013,2014,2015,2016,2017"))
         (("name" . "xdwgfadectl") ("ver" . "2010,2011,2012,2013LT,2013,2014,2015,2016,2017"))
         (("name" . "xedit") ("ver" . "2009,2010,2011,2012,2013LT,2013,2014,2015,2016,2017"))
         (("name" . "xfadectl") ("ver" . "2009,2010,2011,2012,2013LT,2013,2014,2015,2016,2017"))
         (("name" . "xloadctl") ("ver" . "2009,2010,2011,2012,2013LT,2013,2014,2015,2016,2017"))
         (("name" . "xloadpath") ("ver" . "2009,2010,2011,2012,2013LT,2013,2014,2015,2016,2017"))
         (("name" . "xrefctl") ("ver" . "2009,2010,2011,2012,2013LT,2013,2014,2015,2016,2017"))
         (("name" . "xrefnotify") ("ver" . "2009,2010,2011,2012,2013LT,2013,2014,2015,2016,2017"))
         (("name" . "xrefoverride") ("ver" . "2016,2017"))
         (("name" . "xreftype") ("ver" . "2009,2010,2011,2012,2013LT,2013,2014,2015,2016,2017"))
         (("name" . "zoomfactor") ("ver" . "2009,2010,2011,2012,2013LT,2013,2014,2015,2016,2017"))
         (("name" . "zoomwheel") ("ver" . "2009,2010,2011,2012,2013LT,2013,2014,2015,2016,2017"))
         )
      ) ;_ end of setq

(defun _kpblc-eval-value-round
       (value to) ;|
;; http://forum.dwg.ru/showthread.php?p=301275
*    Выполняет округление числа до указанной точности
*    Примеры вызова:
(_kpblc-eval-value-round 16.365 0.01) ; 16.37
|;
  (if (zerop to)
    value
    (* (atoi (rtos (/ (float value) to) 2 0)) to)
    ) ;_ end of if
  ) ;_ end of defun

(defun _kpblc-conv-value-to-string (value /)
  (cond ((= (type value) 'str) value)
        ((= (type value) 'int) (itoa value))
        ((and (= (type value) 'real)
              (equal value (_kpblc-eval-value-round value 1.) 1e-6)
              (equal value (fix value) 1e-6)
              ) ;_ end of and
         (itoa (fix value))
         )
        ((and (= (type value) 'real)
              (equal value (_kpblc-eval-value-round value 1.) 1e-6)
              (not (equal value (fix value) 1e-6))
              ) ;_ end of and
         (rtos value 2)
         )
        ((= (type value) 'real) (rtos value 2 14))
        ((not value) "")
        (t (vl-princ-to-string value))
        ) ;_ end of cond
  ) ;_ end of defun

(defun c:sysvarexport (/ file handle msg) ;|
*    Команда экспортирует значения всех системных переменных в отдельный файл *.txt
|;
  (if (and (setq file (getfiled "Введите имя файла для экспорта системных переменных" "" "txt" 1))
           (/= file "")
           (setq handle (open file "w"))
           ) ;_ end of and
    (progn (foreach item *global-sysvar-list*
             (write-line
               (strcat (strcase (cdr (assoc "name" item)) t)
                       "="
                       (_kpblc-conv-value-to-string (getvar (cdr (assoc "name" item))))
                       ) ;_ end of strcat
               handle
               ) ;_ end of write-line
             ) ;_ end of foreach
           (close handle)
           (setq msg (cons "Данные сохранены в файле " file))
           (alert (strcat (car msg) "\n" (cdr msg)))
           (princ (strcat (car msg) " " (cdr msg)))
           ) ;_ end of progn
    ) ;_ end of if
  (princ)
  ) ;_ end of defun

(defun c:sysvardiff (/ _kpblc-string-replace _kpblc-conv-list-to-string _kpblc-conv-string-to-list file handle sysvar str html_file html_lst f)
                    ;|
*    Команда сравнивает имеющиеся в AutoCAD системные переменные и значения, сохраненные в стороннем
* txt-файле. Отчет выводится в виде html-страницы
|;
  (defun _kpblc-string-replace (str old new)
                               ;|
*    Функция замены вхождений подстроки на новую. Регистронезависима
*    Параметры вызова:
  str  исходная строка
  old  старая строка
  new  новая строка
*    Позволяет менять аналогичные строки: "str" -> "'_str'"
|;  (_kpblc-conv-list-to-string (_kpblc-conv-string-to-list str old) new) ;_ end of _kpblc-conv-list-to-string
    ) ;_ end of defun
  (defun _kpblc-conv-list-to-string (lst sep) ;|
*    Преобразование списка в строку
*    Параметры вызова:
  lst  обрабатываемй список
  sep  разделитель. nil -> " "
|;  (if (and lst
             (setq lst (mapcar (function _kpblc-conv-value-to-string) lst))
             (setq sep (if sep
                         sep
                         " "
                         ) ;_ end of if
                   ) ;_ end of setq
             ) ;_ end of and
      (strcat (car lst)
              (apply (function strcat) (mapcar (function (lambda (x) (strcat sep x))) (cdr lst)))
              ) ;_ end of strcat
      ""
      ) ;_ end of if
    ) ;_ end of defun
  (defun _kpblc-conv-string-to-list (string separator / i)
                                    ;|
*    Функция разбора строки. Возвращает список либо точечную пару. За основу взяты уроки Евгения Елпанова по рекурсиям
*    Параметры вызова:
*  string    разбираемая строка
*  separator  символ, используемый в качестве разделителя частей
*    Примеры вызова:
(_kpblc-conv-string-to-list "1;2;3;4;5;6" ";")  ;-> '(1 2 3 4 5 6)
(_kpblc-conv-string-to-list "1;2" ";")          ;-> '(1 2)
|;  (cond ((= string "") nil)
          ((vl-string-search separator string)
           ((lambda (/ pos res)
              (while (setq pos (vl-string-search separator string))
                (setq res    (cons (substr string 1 pos) res)
                      string (substr string (+ (strlen separator) 1 pos))
                      ) ;_ end of setq
                ) ;_ end of while
              (reverse (cons string res))
              ) ;_ end of lambda
            )
           )
          ((wcmatch (strcase string) (strcat "*" (strcase separator) "*"))
           ((lambda (/ pos res _str prev)
              (setq pos  1
                    prev 1
                    _str (substr string pos)
                    ) ;_ end of setq
              (while (<= pos (1+ (- (strlen string) (strlen separator))))
                (if (wcmatch (strcase (substr string pos (strlen separator))) (strcase separator))
                  (setq res    (cons (substr string 1 (1- pos)) res)
                        string (substr string (+ (strlen separator) pos))
                        pos    0
                        ) ;_ end of setq
                  ) ;_ end of if
                (setq pos (1+ pos))
                ) ;_ end of while
              (if (< (strlen string) (strlen separator))
                (setq res (cons string res))
                ) ;_ end of if
              (if (or (not res) (= _str string))
                (setq res (list string))
                (reverse res)
                ) ;_ end of if
              ) ;_ end of lambda
            )
           )
          (t (list string))
          ) ;_ end of cond
    ) ;_ end of defun
  (if (and (setq file (getfiled "Введите имя файла для сверки системных переменных" "" "txt" 4))
           (/= file "")
           (setq handle (open file "r"))
           ) ;_ end of and
    (progn
      (while (setq str (read-line handle))
        (setq sysvar (cons (cons (substr str 1 (vl-string-search "=" str)) (substr str (+ 2 (vl-string-search "=" str))))
                           sysvar
                           ) ;_ end of cons
              ) ;_ end of setq
        ) ;_ end of while
      (close handle)
      (if (setq sysvar (vl-sort (vl-remove-if
                                  (function
                                    (lambda (x) (or (not (getvar (car x))) (= (cdr x) (_kpblc-conv-value-to-string (getvar (car x))))))
                                    ) ;_ end of function
                                  sysvar
                                  ) ;_ end of vl-remove-if
                                (function (lambda (a b) (< (car a) (car b))))
                                ) ;_ end of vl-sort
                ) ;_ end of setq
        (if (and (setq html_file (getfiled "Введите имя файла отчета" "" "html" 1)) ;_ end of setq
                 html_file
                 (setq handle (open html_file "w"))
                 ) ;_ end of and
          (progn
            (foreach item
                     (append
                       (list
                         "<html><head><title>Результаты сверки состояния системных переменных</title></head>"
                         (strcat "<body><h1>Сверка системных переменных с файлом " file "</h1><br /><br />")
                         "<table cellspasing=\"0\" cellpadding=\"2\" width=\"100%\" border=\"1px\">"
                         "<tr style=\"text-align:center;\"><td width=\"20%\"><strong>Системная переменная</strong><td width=\"25%\"><strong>В файле txt</strong></td><td width=\"25%\"><strong>В AutoCAD</strong></td>"
                         "<td width=\"15%\">Доступна в версиях</td><td width=\"15%\">Сохраняется в</td></tr>"
                         ) ;_ end of list
                       (mapcar (function (lambda (x)
                                           (strcat "<tr"
                                                   (if (setq f (not f))
                                                     ""
                                                     " style=\"background-color: #e5e5e5;\""
                                                     ) ;_ end of if
                                                   "><td>"
                                                   (car x)
                                                   "</td><td>"
                                                   (_kpblc-string-replace
                                                     (_kpblc-string-replace (cdr x) "<" "&lt;") ;_ end of _kpblc-string-replace
                                                     ">"
                                                     "&gt;"
                                                     ) ;_ end of _kpblc-string-replace
                                                   "</td><td  style=\"text-align:center;\">"
                                                   (_kpblc-string-replace
                                                     (_kpblc-string-replace
                                                       (_kpblc-conv-value-to-string (getvar (car x))) ;_ end of _kpblc-conv-value-to-string
                                                       "<"
                                                       "&lt;"
                                                       ) ;_ end of _kpblc-string-replace
                                                     ">"
                                                     "&gt;"
                                                     ) ;_ end of _kpblc-string-replace
                                                   "</td>"
                                                   ;; Доступна в версиях
                                                   "<td>"
                                                   (cdr (assoc "ver"
                                                               (car (vl-remove-if-not
                                                                      (function (lambda (x1)
                                                                                  (= (strcase (cdr (assoc "name" x1))) ;_ end of strcase
                                                                                     (strcase (car x))
                                                                                     ) ;_ end of =
                                                                                  ) ;_ end of lambda
                                                                                ) ;_ end of function
                                                                      *global-sysvar-list*
                                                                      ) ;_ end of vl-remove-if-not
                                                                    ) ;_ end of car
                                                               ) ;_ end of assoc
                                                        ) ;_ end of cdr
                                                   "</td>"
                                                   ;; Сохраняется в...
                                                   "<td></td>"
                                                   "</tr>"
                                                   ) ;_ end of strcat
                                           ) ;_ end of lambda
                                         ) ;_ end of function
                               sysvar
                               ) ;_ end of mapcar
                       '("</table></body></html>")
                       ) ;_ end of append
              (write-line item handle)
              ) ;_ end of foreach
            (close handle)
            (command "_.browser" html_file)
            ) ;_ end of progn
          ) ;_ end of if
        (alert "Разница не обнаружена!")
        ) ;_ end of if
      ) ;_ end of progn
    ) ;_ end of if
  ) ;_ end of defun
