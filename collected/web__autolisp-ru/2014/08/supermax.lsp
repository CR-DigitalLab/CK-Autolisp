;listprop - список с указателем ename блока

;=== проверяем блок на вшивость, то есть динамический он или нет? =========================================
; заодно сохраняем в r_e список всех свойств блока, а в r_w - список видимых свойств блока
(setq r_w nil)
(mapcar (function (lambda (x) (if (not (vl-catch-all-error-p (vl-catch-all-apply 'vlax-safearray->list (list (setq r_e (vlax-variant-value 
  (vlax-invoke-method x "GetDynamicBlockProperties") ) ) ) ) ) )
(setq r_w (append (vl-remove-if (function (lambda (x) (= (vla-get-Show x) :vlax-true))) (vlax-safearray->list r_e)) r_w)))
))  listprop)

;==========  получаем словарь "ACAD_EVALUATION_GRAPH" =============================================
; указатель на него записан в lst_dict
(defun prop_block ()
;Находим эффективное имя блока и по нему находим в базе блоков его полное описание
(setq lst_name_block (entget (TBLOBJNAME "block" (vla-get-EffectiveName (car listprop))) '("*")))
(setq slov_block (cdr (assoc 330 lst_name_block)))  ;Выбираем словарь со свойствами этого блока
(setq dxf_slov_block (entget slov_block))  ;Получаем список DXF-кодов этого словаря
(setq wq-w_block (entget (cdr (assoc 360 dxf_slov_block)))) ;Выбираем из этого списка словарь и получаем его DXF-коды
;Получаем содержание словаря со свойствами блока и их DXF-сопровождением
(setq lst_dict (car (mapcar 'cdr (vl-remove-if-not '(lambda(x) 
  (and (= (car x) 360) (= (cdr (assoc 0 (entget (cdr x)))) "ACAD_EVALUATION_GRAPH"))) wq-w_block))))
)

;======== определяем, есть параметры visibility-set или нет? ==============================================
; если visibility-set-ы есть, то в переменную BLC-VIS-PAR записаны на них указатели. В 301 пару записаны их имена
(setq BLC-VIS-PAR nil)
(mapcar '(lambda (x) 
  (if (and (= (car x) 360) 
           (= (cdr (assoc 0 (entget (cdr x)))) "BLOCKVISIBILITYPARAMETER"))
      (setq BLC-VIS-PAR (cons (cdr x) BLC-VIS-PAR) ) )) (entget lst_dict))

;======== если параметров visibility-set нет, то есть BLC-VIS-PAR = nil =======================================
; то переменная r_w содержит окончательный список видимых свойств 
(setq r_u nil)
(if (not (null r_w)) (mapcar (function (lambda (x) 
(setq r_u (cons (list (vla-get-PropertyName x) (vlax-variant-value (vla-get-Value x))) r_u))
))
r_w))
(mapcar (function (lambda (x) (if (= (vl-prin1-to-string (type (cadr x))) "safearray") (setq r_u (subst (cons (car x) (vlax-safearray->list (cadr x))) x r_u))))) r_u)

;=============================================================================================
; потом допишу остальное

[/cc]

Распечатка с "BLOCKVISIBILITYPARAMETER"
[cc lang="lisp"]
((-1 . <Имя объекта: 7ed57cb0>) (0 . "BLOCKVISIBILITYPARAMETER") 
(330 . <Имя объекта: 7ed57c90>) (5 . "7326") (100 . "AcDbEvalExpr") 
(90 . 1) (98 . 29) (99 . 37) 
(100 . "AcDbBlockElement") 
(300 . "Visibility State") 
(98 . 29) 
(99 . 37) 
(1071 . 0) (100 . "AcDbBlockParameter") 
(280 . 0) 
(281 . 0) 
(100 . "AcDbBlock1PtParameter") 
(1010 45.9216 -48.8186 0.0) (93 . 0) (170 . 0) (171 . 0) (100 . "AcDbBlockVisibilityParameter") 
(281 . 1) 
(301 . "Visibility") 
(302 . "") 
(91 . 0) 
(93 . 71) 
(331 . <Имя объекта: 7ed58260>) (331 . <Имя объекта: 7ed58268>) (331 . <Имя объекта: 7ed58270>) (331 . <Имя объекта: 7ed58278>) 
(331 . <Имя объекта: 7ed58280>) (331 . <Имя объекта: 7ed58288>) (331 . <Имя объекта: 7ed58290>) (331 . <Имя объекта: 7ed58298>) 
(331 . <Имя объекта: 7ed582a0>) (331 . <Имя объекта: 7ed582a8>) (331 . <Имя объекта: 7ed582b0>) (331 . <Имя объекта: 7ed582b8>) 
(331 . <Имя объекта: 7ed582c0>) (331 . <Имя объекта: 7ed582c8>) (331 . <Имя объекта: 7ed582d0>) (331 . <Имя объекта: 7ed582d8>) 
(331 . <Имя объекта: 7ed582e0>) (331 . <Имя объекта: 7ed582e8>) (331 . <Имя объекта: 7ed582f0>) (331 . <Имя объекта: 7ed582f8>) 
(331 . <Имя объекта: 7ed58300>) (331 . <Имя объекта: 7ed58308>) (331 . <Имя объекта: 7ed58310>) (331 . <Имя объекта: 7ed58318>) 
(331 . <Имя объекта: 7ed58320>) (331 . <Имя объекта: 7ed58328>) (331 . <Имя объекта: 7ed58330>) (331 . <Имя объекта: 7ed58338>) 
(331 . <Имя объекта: 7ed58340>) (331 . <Имя объекта: 7ed58348>) (331 . <Имя объекта: 7ed58350>) (331 . <Имя объекта: 7ed58358>) 
(331 . <Имя объекта: 7ed58360>) (331 . <Имя объекта: 7ed58368>) (331 . <Имя объекта: 7ed58370>) (331 . <Имя объекта: 7ed58378>) 
(331 . <Имя объекта: 7ed58380>) (331 . <Имя объекта: 7ed58388>) (331 . <Имя объекта: 7ed58390>) (331 . <Имя объекта: 7ed58398>) 
(331 . <Имя объекта: 7ed583a0>) (331 . <Имя объекта: 7ed583a8>) (331 . <Имя объекта: 7ed583b0>) (331 . <Имя объекта: 7ed583b8>) 
(331 . <Имя объекта: 7ed58400>) (331 . <Имя объекта: 7ed58408>) (331 . <Имя объекта: 7ed58410>) (331 . <Имя объекта: 7ed58418>) 
(331 . <Имя объекта: 7ed58420>) (331 . <Имя объекта: 7ed58428>) (331 . <Имя объекта: 7ed58430>) (331 . <Имя объекта: 7ed58438>) 
(331 . <Имя объекта: 7ed58440>) (331 . <Имя объекта: 7ed58448>) (331 . <Имя объекта: 7ed58450>) (331 . <Имя объекта: 7ed58458>) 
(331 . <Имя объекта: 7ed58460>) (331 . <Имя объекта: 7ed58468>) (331 . <Имя объекта: 7ed58470>) (331 . <Имя объекта: 7ed58478>) 
(331 . <Имя объекта: 7ed58480>) (331 . <Имя объекта: 7ed58488>) (331 . <Имя объекта: 7ed58490>) (331 . <Имя объекта: 7ed58498>) 
(331 . <Имя объекта: 7ed584a0>) (331 . <Имя объекта: 7ed584a8>) (331 . <Имя объекта: 7ed584b0>) (331 . <Имя объекта: 7ed584b8>) 
(331 . <Имя объекта: 7ed584c0>) (331 . <Имя объекта: 7ed584c8>) (331 . <Имя объекта: 7ed584d0>) 
(92 . 3) 
(303 . "Группа-1") 
(94 . 24) 
(332 . <Имя объекта: 7ed58260>) (332 . <Имя объекта: 7ed58268>) (332 . <Имя объекта: 7ed58270>) (332 . <Имя объекта: 7ed58278>) 
(332 . <Имя объекта: 7ed58280>) (332 . <Имя объекта: 7ed58288>) (332 . <Имя объекта: 7ed58290>) (332 . <Имя объекта: 7ed58298>) 
(332 . <Имя объекта: 7ed582a0>) (332 . <Имя объекта: 7ed582a8>) (332 . <Имя объекта: 7ed582b0>) (332 . <Имя объекта: 7ed582b8>) 
(332 . <Имя объекта: 7ed582c0>) (332 . <Имя объекта: 7ed582c8>) (332 . <Имя объекта: 7ed582d0>) (332 . <Имя объекта: 7ed58478>) 
(332 . <Имя объекта: 7ed58480>) (332 . <Имя объекта: 7ed58488>) (332 . <Имя объекта: 7ed58490>) (332 . <Имя объекта: 7ed58498>) 
(332 . <Имя объекта: 7ed584a0>) (332 . <Имя объекта: 7ed584a8>) (332 . <Имя объекта: 7ed584b0>) (332 . <Имя объекта: 7ed584b8>) 
(95 . 167) 
(333 . <Имя объекта: 7ed58248>) (333 . <Имя объекта: 7ed57d40>) (333 . <Имя объекта: 7ed57e00>) (333 . <Имя объекта: 7ed57df0>) 
(333 . <Имя объекта: 7ed57de0>) (333 . <Имя объекта: 7ed57dd0>) (333 . <Имя объекта: 7ed57dc0>) (333 . <Имя объекта: 7ed58208>) 
(333 . <Имя объекта: 7ed57db0>) (333 . <Имя объекта: 7ed57da8>) (333 . <Имя объекта: 7ed57d50>) (333 . <Имя объекта: 7ed58238>) 
(333 . <Имя объекта: 7ed58218>) (333 . <Имя объекта: 7ed58220>) (333 . <Имя объекта: 7ed581f0>) (333 . <Имя объекта: 7ed58210>) 
(333 . <Имя объекта: 7ed581e0>) (333 . <Имя объекта: 7ed58200>) (333 . <Имя объекта: 7ed581d0>) (333 . <Имя объекта: 7ed581f8>) 
(333 . <Имя объекта: 7ed581c0>) (333 . <Имя объекта: 7ed581e8>) (333 . <Имя объекта: 7ed581b0>) (333 . <Имя объекта: 7ed581d8>) 
(333 . <Имя объекта: 7ed581a0>) (333 . <Имя объекта: 7ed581c8>) (333 . <Имя объекта: 7ed58190>) (333 . <Имя объекта: 7ed581b8>) 
(333 . <Имя объекта: 7ed58180>) (333 . <Имя объекта: 7ed581a8>) (333 . <Имя объекта: 7ed58170>) (333 . <Имя объекта: 7ed58198>) 
(333 . <Имя объекта: 7ed58160>) (333 . <Имя объекта: 7ed58188>) (333 . <Имя объекта: 7ed58150>) (333 . <Имя объекта: 7ed58178>) 
(333 . <Имя объекта: 7ed58140>) (333 . <Имя объекта: 7ed58168>) (333 . <Имя объекта: 7ed58130>) (333 . <Имя объекта: 7ed58158>) 
(333 . <Имя объекта: 7ed58120>) (333 . <Имя объекта: 7ed58148>) (333 . <Имя объекта: 7ed58110>) (333 . <Имя объекта: 7ed58138>) 
(333 . <Имя объекта: 7ed58100>) (333 . <Имя объекта: 7ed58128>) (333 . <Имя объекта: 7ed580f0>) (333 . <Имя объекта: 7ed58118>) 
(333 . <Имя объекта: 7ed580e0>) (333 . <Имя объекта: 7ed58108>) (333 . <Имя объекта: 7ed580d0>) (333 . <Имя объекта: 7ed580f8>) 
(333 . <Имя объекта: 7ed580c0>) (333 . <Имя объекта: 7ed580e8>) (333 . <Имя объекта: 7ed580b0>) (333 . <Имя объекта: 7ed580d8>) 
(333 . <Имя объекта: 7ed580a0>) (333 . <Имя объекта: 7ed580c8>) (333 . <Имя объекта: 7ed58090>) (333 . <Имя объекта: 7ed580b8>) 
(333 . <Имя объекта: 7ed58080>) (333 . <Имя объекта: 7ed580a8>) (333 . <Имя объекта: 7ed58070>) (333 . <Имя объекта: 7ed58098>) 
(333 . <Имя объекта: 7ed58060>) (333 . <Имя объекта: 7ed58088>) (333 . <Имя объекта: 7ed58050>) (333 . <Имя объекта: 7ed58078>) 
(333 . <Имя объекта: 7ed58040>) (333 . <Имя объекта: 7ed58068>) (333 . <Имя объекта: 7ed58030>) (333 . <Имя объекта: 7ed58058>) 
(333 . <Имя объекта: 7ed58020>) (333 . <Имя объекта: 7ed58048>) (333 . <Имя объекта: 7ed58010>) (333 . <Имя объекта: 7ed58038>) 
(333 . <Имя объекта: 7ed58000>) (333 . <Имя объекта: 7ed58028>) (333 . <Имя объекта: 7ed57fb0>) (333 . <Имя объекта: 7ed58018>) 
(333 . <Имя объекта: 7ed57fa0>) (333 . <Имя объекта: 7ed58008>) (333 . <Имя объекта: 7ed57f90>) (333 . <Имя объекта: 7ed57fb8>) 
(333 . <Имя объекта: 7ed57f80>) (333 . <Имя объекта: 7ed57fa8>) (333 . <Имя объекта: 7ed57f70>) (333 . <Имя объекта: 7ed57f98>) 
(333 . <Имя объекта: 7ed57f60>) (333 . <Имя объекта: 7ed57f88>) (333 . <Имя объекта: 7ed57f50>) (333 . <Имя объекта: 7ed57f78>) 
(333 . <Имя объекта: 7ed57f40>) (333 . <Имя объекта: 7ed57f68>) (333 . <Имя объекта: 7ed57f30>) (333 . <Имя объекта: 7ed57f58>) 
(333 . <Имя объекта: 7ed57f20>) (333 . <Имя объекта: 7ed57f48>) (333 . <Имя объекта: 7ed57f10>) (333 . <Имя объекта: 7ed57f38>) 
(333 . <Имя объекта: 7ed57f00>) (333 . <Имя объекта: 7ed57f28>) (333 . <Имя объекта: 7ed57ef0>) (333 . <Имя объекта: 7ed57f18>) 
(333 . <Имя объекта: 7ed57ee0>) (333 . <Имя объекта: 7ed57f08>) (333 . <Имя объекта: 7ed57ed0>) (333 . <Имя объекта: 7ed57ef8>) 
(333 . <Имя объекта: 7ed57ec0>) (333 . <Имя объекта: 7ed57ee8>) (333 . <Имя объекта: 7ed57eb0>) (333 . <Имя объекта: 7ed57ed8>) 
(333 . <Имя объекта: 7ed57ea0>) (333 . <Имя объекта: 7ed57ec8>) (333 . <Имя объекта: 7ed57e90>) (333 . <Имя объекта: 7ed57eb8>) 
(333 . <Имя объекта: 7ed57e80>) (333 . <Имя объекта: 7ed57ea8>) (333 . <Имя объекта: 7ed57e70>) (333 . <Имя объекта: 7ed57e98>) 
(333 . <Имя объекта: 7ed57e60>) (333 . <Имя объекта: 7ed57e88>) (333 . <Имя объекта: 7ed57e50>) (333 . <Имя объекта: 7ed57e78>) 
(333 . <Имя объекта: 7ed57e40>) (333 . <Имя объекта: 7ed57e68>) (333 . <Имя объекта: 7ed57e30>) (333 . <Имя объекта: 7ed57e58>) 
(333 . <Имя объекта: 7ed57e20>) (333 . <Имя объекта: 7ed57e48>) (333 . <Имя объекта: 7ed57e10>) (333 . <Имя объекта: 7ed57e38>) 
(333 . <Имя объекта: 7ed57e28>) (333 . <Имя объекта: 7ed57e18>) (333 . <Имя объекта: 7ed57e08>) (333 . <Имя объекта: 7ed57df8>) 
(333 . <Имя объекта: 7ed57de8>) (333 . <Имя объекта: 7ed57dd8>) (333 . <Имя объекта: 7ed57dc8>) (333 . <Имя объекта: 7ed57db8>) 
(333 . <Имя объекта: 7ed58228>) (333 . <Имя объекта: 7ed57da0>) (333 . <Имя объекта: 7ed57d98>) (333 . <Имя объекта: 7ed57d90>) 
(333 . <Имя объекта: 7ed57d88>) (333 . <Имя объекта: 7ed57d80>) (333 . <Имя объекта: 7ed57d78>) (333 . <Имя объекта: 7ed57d70>) 
(333 . <Имя объекта: 7ed58240>) (333 . <Имя объекта: 7ed57d68>) (333 . <Имя объекта: 7ed58230>) (333 . <Имя объекта: 7ed57d30>) 
(333 . <Имя объекта: 7ed57d60>) (333 . <Имя объекта: 7ed57d38>) (333 . <Имя объекта: 7ed57d20>) (333 . <Имя объекта: 7ed57d28>) 
(333 . <Имя объекта: 7ed57d18>) (333 . <Имя объекта: 7ed57d10>) (333 . <Имя объекта: 7ed57d00>) (333 . <Имя объекта: 7ed57ce8>) 
(333 . <Имя объекта: 7ed57cf0>) (333 . <Имя объекта: 7ed57cd0>) (333 . <Имя объекта: 7ed57ce0>) (333 . <Имя объекта: 7ed57cd8>) 
(333 . <Имя объекта: 7ed57cc0>) (333 . <Имя объекта: 7ed57cc8>) (333 . <Имя объекта: 7ed57cb8>) 
(303 . "Группа-2") 
(94 . 24) 
(332 . <Имя объекта: 7ed58260>) (332 . <Имя объекта: 7ed58268>) (332 . <Имя объекта: 7ed58270>) (332 . <Имя объекта: 7ed58278>) 
(332 . <Имя объекта: 7ed58280>) (332 . <Имя объекта: 7ed58288>) (332 . <Имя объекта: 7ed58290>) (332 . <Имя объекта: 7ed58298>) 
(332 . <Имя объекта: 7ed582a0>) (332 . <Имя объекта: 7ed582a8>) (332 . <Имя объекта: 7ed582b0>) (332 . <Имя объекта: 7ed582b8>) 
(332 . <Имя объекта: 7ed582c0>) (332 . <Имя объекта: 7ed582c8>) (332 . <Имя объекта: 7ed582d0>) (332 . <Имя объекта: 7ed58478>) 
(332 . <Имя объекта: 7ed58480>) (332 . <Имя объекта: 7ed58488>) (332 . <Имя объекта: 7ed58490>) (332 . <Имя объекта: 7ed58498>) 
(332 . <Имя объекта: 7ed584a0>) (332 . <Имя объекта: 7ed584a8>) (332 . <Имя объекта: 7ed584b0>) (332 . <Имя объекта: 7ed584b8>) 
(95 . 167) 
(333 . <Имя объекта: 7ed58248>) (333 . <Имя объекта: 7ed57d40>) (333 . <Имя объекта: 7ed57e00>) (333 . <Имя объекта: 7ed57df0>) 
(333 . <Имя объекта: 7ed57de0>) (333 . <Имя объекта: 7ed57dd0>) (333 . <Имя объекта: 7ed57dc0>) (333 . <Имя объекта: 7ed58208>) 
(333 . <Имя объекта: 7ed57db0>) (333 . <Имя объекта: 7ed57da8>) (333 . <Имя объекта: 7ed57d50>) (333 . <Имя объекта: 7ed58238>) 
(333 . <Имя объекта: 7ed58218>) (333 . <Имя объекта: 7ed58220>) (333 . <Имя объекта: 7ed581f0>) (333 . <Имя объекта: 7ed58210>) 
(333 . <Имя объекта: 7ed581e0>) (333 . <Имя объекта: 7ed58200>) (333 . <Имя объекта: 7ed581d0>) (333 . <Имя объекта: 7ed581f8>) 
(333 . <Имя объекта: 7ed581c0>) (333 . <Имя объекта: 7ed581e8>) (333 . <Имя объекта: 7ed581b0>) (333 . <Имя объекта: 7ed581d8>) 
(333 . <Имя объекта: 7ed581a0>) (333 . <Имя объекта: 7ed581c8>) (333 . <Имя объекта: 7ed58190>) (333 . <Имя объекта: 7ed581b8>) 
(333 . <Имя объекта: 7ed58180>) (333 . <Имя объекта: 7ed581a8>) (333 . <Имя объекта: 7ed58170>) (333 . <Имя объекта: 7ed58198>) 
(333 . <Имя объекта: 7ed58160>) (333 . <Имя объекта: 7ed58188>) (333 . <Имя объекта: 7ed58150>) (333 . <Имя объекта: 7ed58178>) 
(333 . <Имя объекта: 7ed58140>) (333 . <Имя объекта: 7ed58168>) (333 . <Имя объекта: 7ed58130>) (333 . <Имя объекта: 7ed58158>) 
(333 . <Имя объекта: 7ed58120>) (333 . <Имя объекта: 7ed58148>) (333 . <Имя объекта: 7ed58110>) (333 . <Имя объекта: 7ed58138>) 
(333 . <Имя объекта: 7ed58100>) (333 . <Имя объекта: 7ed58128>) (333 . <Имя объекта: 7ed580f0>) (333 . <Имя объекта: 7ed58118>) 
(333 . <Имя объекта: 7ed580e0>) (333 . <Имя объекта: 7ed58108>) (333 . <Имя объекта: 7ed580d0>) (333 . <Имя объекта: 7ed580f8>) 
(333 . <Имя объекта: 7ed580c0>) (333 . <Имя объекта: 7ed580e8>) (333 . <Имя объекта: 7ed580b0>) (333 . <Имя объекта: 7ed580d8>) 
(333 . <Имя объекта: 7ed580a0>) (333 . <Имя объекта: 7ed580c8>) (333 . <Имя объекта: 7ed58090>) (333 . <Имя объекта: 7ed580b8>) 
(333 . <Имя объекта: 7ed58080>) (333 . <Имя объекта: 7ed580a8>) (333 . <Имя объекта: 7ed58070>) (333 . <Имя объекта: 7ed58098>) 
(333 . <Имя объекта: 7ed58060>) (333 . <Имя объекта: 7ed58088>) (333 . <Имя объекта: 7ed58050>) (333 . <Имя объекта: 7ed58078>) 
(333 . <Имя объекта: 7ed58040>) (333 . <Имя объекта: 7ed58068>) (333 . <Имя объекта: 7ed58030>) (333 . <Имя объекта: 7ed58058>) 
(333 . <Имя объекта: 7ed58020>) (333 . <Имя объекта: 7ed58048>) (333 . <Имя объекта: 7ed58010>) (333 . <Имя объекта: 7ed58038>) 
(333 . <Имя объекта: 7ed58000>) (333 . <Имя объекта: 7ed58028>) (333 . <Имя объекта: 7ed57fb0>) (333 . <Имя объекта: 7ed58018>) 
(333 . <Имя объекта: 7ed57fa0>) (333 . <Имя объекта: 7ed58008>) (333 . <Имя объекта: 7ed57f90>) (333 . <Имя объекта: 7ed57fb8>) 
(333 . <Имя объекта: 7ed57f80>) (333 . <Имя объекта: 7ed57fa8>) (333 . <Имя объекта: 7ed57f70>) (333 . <Имя объекта: 7ed57f98>) 
(333 . <Имя объекта: 7ed57f60>) (333 . <Имя объекта: 7ed57f88>) (333 . <Имя объекта: 7ed57f50>) (333 . <Имя объекта: 7ed57f78>) 
(333 . <Имя объекта: 7ed57f40>) (333 . <Имя объекта: 7ed57f68>) (333 . <Имя объекта: 7ed57f30>) (333 . <Имя объекта: 7ed57f58>) 
(333 . <Имя объекта: 7ed57f20>) (333 . <Имя объекта: 7ed57f48>) (333 . <Имя объекта: 7ed57f10>) (333 . <Имя объекта: 7ed57f38>) 
(333 . <Имя объекта: 7ed57f00>) (333 . <Имя объекта: 7ed57f28>) (333 . <Имя объекта: 7ed57ef0>) (333 . <Имя объекта: 7ed57f18>) 
(333 . <Имя объекта: 7ed57ee0>) (333 . <Имя объекта: 7ed57f08>) (333 . <Имя объекта: 7ed57ed0>) (333 . <Имя объекта: 7ed57ef8>) 
(333 . <Имя объекта: 7ed57ec0>) (333 . <Имя объекта: 7ed57ee8>) (333 . <Имя объекта: 7ed57eb0>) (333 . <Имя объекта: 7ed57ed8>) 
(333 . <Имя объекта: 7ed57ea0>) (333 . <Имя объекта: 7ed57ec8>) (333 . <Имя объекта: 7ed57e90>) (333 . <Имя объекта: 7ed57eb8>) 
(333 . <Имя объекта: 7ed57e80>) (333 . <Имя объекта: 7ed57ea8>) (333 . <Имя объекта: 7ed57e70>) (333 . <Имя объекта: 7ed57e98>) 
(333 . <Имя объекта: 7ed57e60>) (333 . <Имя объекта: 7ed57e88>) (333 . <Имя объекта: 7ed57e50>) (333 . <Имя объекта: 7ed57e78>) 
(333 . <Имя объекта: 7ed57e40>) (333 . <Имя объекта: 7ed57e68>) (333 . <Имя объекта: 7ed57e30>) (333 . <Имя объекта: 7ed57e58>) 
(333 . <Имя объекта: 7ed57e20>) (333 . <Имя объекта: 7ed57e48>) (333 . <Имя объекта: 7ed57e10>) (333 . <Имя объекта: 7ed57e38>) 
(333 . <Имя объекта: 7ed57e28>) (333 . <Имя объекта: 7ed57e18>) (333 . <Имя объекта: 7ed57e08>) (333 . <Имя объекта: 7ed57df8>) 
(333 . <Имя объекта: 7ed57de8>) (333 . <Имя объекта: 7ed57dd8>) (333 . <Имя объекта: 7ed57dc8>) (333 . <Имя объекта: 7ed57db8>) 
(333 . <Имя объекта: 7ed58228>) (333 . <Имя объекта: 7ed57da0>) (333 . <Имя объекта: 7ed57d98>) (333 . <Имя объекта: 7ed57d90>) 
(333 . <Имя объекта: 7ed57d88>) (333 . <Имя объекта: 7ed57d80>) (333 . <Имя объекта: 7ed57d78>) (333 . <Имя объекта: 7ed57d70>) 
(333 . <Имя объекта: 7ed58240>) (333 . <Имя объекта: 7ed57d68>) (333 . <Имя объекта: 7ed58230>) (333 . <Имя объекта: 7ed57d30>) 
(333 . <Имя объекта: 7ed57d48>) (333 . <Имя объекта: 7ed57d60>) (333 . <Имя объекта: 7ed57d20>) (333 . <Имя объекта: 7ed57d28>) 
(333 . <Имя объекта: 7ed57d10>) (333 . <Имя объекта: 7ed57cf8>) (333 . <Имя объекта: 7ed57d00>) (333 . <Имя объекта: 7ed57ce8>) 
(333 . <Имя объекта: 7ed57cf0>) (333 . <Имя объекта: 7ed57cd0>) (333 . <Имя объекта: 7ed57ce0>) (333 . <Имя объекта: 7ed57cd8>) 
(333 . <Имя объекта: 7ed57cc0>) (333 . <Имя объекта: 7ed57cc8>) (333 . <Имя объекта: 7ed57cb8>) 
(303 . "Группа-3") 
(94 . 24) 
(332 . <Имя объекта: 7ed58260>) (332 . <Имя объекта: 7ed58268>) (332 . <Имя объекта: 7ed58270>) (332 . <Имя объекта: 7ed58278>) 
(332 . <Имя объекта: 7ed58280>) (332 . <Имя объекта: 7ed58288>) (332 . <Имя объекта: 7ed58290>) (332 . <Имя объекта: 7ed58298>) 
(332 . <Имя объекта: 7ed582a0>) (332 . <Имя объекта: 7ed582a8>) (332 . <Имя объекта: 7ed582b0>) (332 . <Имя объекта: 7ed582b8>) 
(332 . <Имя объекта: 7ed582c0>) (332 . <Имя объекта: 7ed582c8>) (332 . <Имя объекта: 7ed582d0>) (332 . <Имя объекта: 7ed58478>) 
(332 . <Имя объекта: 7ed58480>) (332 . <Имя объекта: 7ed58488>) (332 . <Имя объекта: 7ed58490>) (332 . <Имя объекта: 7ed58498>) 
(332 . <Имя объекта: 7ed584a0>) (332 . <Имя объекта: 7ed584a8>) (332 . <Имя объекта: 7ed584b0>) (332 . <Имя объекта: 7ed584b8>) 
(95 . 167) 
(333 . <Имя объекта: 7ed58248>) (333 . <Имя объекта: 7ed57d40>) (333 . <Имя объекта: 7ed57e00>) (333 . <Имя объекта: 7ed57df0>) 
(333 . <Имя объекта: 7ed57de0>) (333 . <Имя объекта: 7ed57dd0>) (333 . <Имя объекта: 7ed57dc0>) (333 . <Имя объекта: 7ed58208>) 
(333 . <Имя объекта: 7ed57db0>) (333 . <Имя объекта: 7ed57da8>) (333 . <Имя объекта: 7ed57d50>) (333 . <Имя объекта: 7ed58238>) 
(333 . <Имя объекта: 7ed58218>) (333 . <Имя объекта: 7ed58220>) (333 . <Имя объекта: 7ed581f0>) (333 . <Имя объекта: 7ed58210>) 
(333 . <Имя объекта: 7ed581e0>) (333 . <Имя объекта: 7ed58200>) (333 . <Имя объекта: 7ed581d0>) (333 . <Имя объекта: 7ed581f8>) 
(333 . <Имя объекта: 7ed581c0>) (333 . <Имя объекта: 7ed581e8>) (333 . <Имя объекта: 7ed581b0>) (333 . <Имя объекта: 7ed581d8>) 
(333 . <Имя объекта: 7ed581a0>) (333 . <Имя объекта: 7ed581c8>) (333 . <Имя объекта: 7ed58190>) (333 . <Имя объекта: 7ed581b8>) 
(333 . <Имя объекта: 7ed58180>) (333 . <Имя объекта: 7ed581a8>) (333 . <Имя объекта: 7ed58170>) (333 . <Имя объекта: 7ed58198>) 
(333 . <Имя объекта: 7ed58160>) (333 . <Имя объекта: 7ed58188>) (333 . <Имя объекта: 7ed58150>) (333 . <Имя объекта: 7ed58178>) 
(333 . <Имя объекта: 7ed58140>) (333 . <Имя объекта: 7ed58168>) (333 . <Имя объекта: 7ed58130>) (333 . <Имя объекта: 7ed58158>) 
(333 . <Имя объекта: 7ed58120>) (333 . <Имя объекта: 7ed58148>) (333 . <Имя объекта: 7ed58110>) (333 . <Имя объекта: 7ed58138>) 
(333 . <Имя объекта: 7ed58100>) (333 . <Имя объекта: 7ed58128>) (333 . <Имя объекта: 7ed580f0>) (333 . <Имя объекта: 7ed58118>) 
(333 . <Имя объекта: 7ed580e0>) (333 . <Имя объекта: 7ed58108>) (333 . <Имя объекта: 7ed580d0>) (333 . <Имя объекта: 7ed580f8>) 
(333 . <Имя объекта: 7ed580c0>) (333 . <Имя объекта: 7ed580e8>) (333 . <Имя объекта: 7ed580b0>) (333 . <Имя объекта: 7ed580d8>) 
(333 . <Имя объекта: 7ed580a0>) (333 . <Имя объекта: 7ed580c8>) (333 . <Имя объекта: 7ed58090>) (333 . <Имя объекта: 7ed580b8>) 
(333 . <Имя объекта: 7ed58080>) (333 . <Имя объекта: 7ed580a8>) (333 . <Имя объекта: 7ed58070>) (333 . <Имя объекта: 7ed58098>) 
(333 . <Имя объекта: 7ed58060>) (333 . <Имя объекта: 7ed58088>) (333 . <Имя объекта: 7ed58050>) (333 . <Имя объекта: 7ed58078>) 
(333 . <Имя объекта: 7ed58040>) (333 . <Имя объекта: 7ed58068>) (333 . <Имя объекта: 7ed58030>) (333 . <Имя объекта: 7ed58058>) 
(333 . <Имя объекта: 7ed58020>) (333 . <Имя объекта: 7ed58048>) (333 . <Имя объекта: 7ed58010>) (333 . <Имя объекта: 7ed58038>) 
(333 . <Имя объекта: 7ed58000>) (333 . <Имя объекта: 7ed58028>) (333 . <Имя объекта: 7ed57fb0>) (333 . <Имя объекта: 7ed58018>) 
(333 . <Имя объекта: 7ed57fa0>) (333 . <Имя объекта: 7ed58008>) (333 . <Имя объекта: 7ed57f90>) (333 . <Имя объекта: 7ed57fb8>) 
(333 . <Имя объекта: 7ed57f80>) (333 . <Имя объекта: 7ed57fa8>) (333 . <Имя объекта: 7ed57f70>) (333 . <Имя объекта: 7ed57f98>) 
(333 . <Имя объекта: 7ed57f60>) (333 . <Имя объекта: 7ed57f88>) (333 . <Имя объекта: 7ed57f50>) (333 . <Имя объекта: 7ed57f78>) 
(333 . <Имя объекта: 7ed57f40>) (333 . <Имя объекта: 7ed57f68>) (333 . <Имя объекта: 7ed57f30>) (333 . <Имя объекта: 7ed57f58>) 
(333 . <Имя объекта: 7ed57f20>) (333 . <Имя объекта: 7ed57f48>) (333 . <Имя объекта: 7ed57f10>) (333 . <Имя объекта: 7ed57f38>) 
(333 . <Имя объекта: 7ed57f00>) (333 . <Имя объекта: 7ed57f28>) (333 . <Имя объекта: 7ed57ef0>) (333 . <Имя объекта: 7ed57f18>) 
(333 . <Имя объекта: 7ed57ee0>) (333 . <Имя объекта: 7ed57f08>) (333 . <Имя объекта: 7ed57ed0>) (333 . <Имя объекта: 7ed57ef8>) 
(333 . <Имя объекта: 7ed57ec0>) (333 . <Имя объекта: 7ed57ee8>) (333 . <Имя объекта: 7ed57eb0>) (333 . <Имя объекта: 7ed57ed8>) 
(333 . <Имя объекта: 7ed57ea0>) (333 . <Имя объекта: 7ed57ec8>) (333 . <Имя объекта: 7ed57e90>) (333 . <Имя объекта: 7ed57eb8>) 
(333 . <Имя объекта: 7ed57e80>) (333 . <Имя объекта: 7ed57ea8>) (333 . <Имя объекта: 7ed57e70>) (333 . <Имя объекта: 7ed57e98>) 
(333 . <Имя объекта: 7ed57e60>) (333 . <Имя объекта: 7ed57e88>) (333 . <Имя объекта: 7ed57e50>) (333 . <Имя объекта: 7ed57e78>) 
(333 . <Имя объекта: 7ed57e40>) (333 . <Имя объекта: 7ed57e68>) (333 . <Имя объекта: 7ed57e30>) (333 . <Имя объекта: 7ed57e58>) 
(333 . <Имя объекта: 7ed57e20>) (333 . <Имя объекта: 7ed57e48>) (333 . <Имя объекта: 7ed57e10>) (333 . <Имя объекта: 7ed57e38>) 
(333 . <Имя объекта: 7ed57e28>) (333 . <Имя объекта: 7ed57e18>) (333 . <Имя объекта: 7ed57e08>) (333 . <Имя объекта: 7ed57df8>) 
(333 . <Имя объекта: 7ed57de8>) (333 . <Имя объекта: 7ed57dd8>) (333 . <Имя объекта: 7ed57dc8>) (333 . <Имя объекта: 7ed57db8>) 
(333 . <Имя объекта: 7ed58228>) (333 . <Имя объекта: 7ed57da0>) (333 . <Имя объекта: 7ed57d98>) (333 . <Имя объекта: 7ed57d90>) 
(333 . <Имя объекта: 7ed57d88>) (333 . <Имя объекта: 7ed57d80>) (333 . <Имя объекта: 7ed57d78>) (333 . <Имя объекта: 7ed57d70>) 
(333 . <Имя объекта: 7ed58240>) (333 . <Имя объекта: 7ed57d68>) (333 . <Имя объекта: 7ed58230>) (333 . <Имя объекта: 7ed57d58>) 
(333 . <Имя объекта: 7ed57d30>) (333 . <Имя объекта: 7ed57d60>) (333 . <Имя объекта: 7ed57d20>) (333 . <Имя объекта: 7ed57d28>) 
(333 . <Имя объекта: 7ed57d08>) (333 . <Имя объекта: 7ed57d10>) (333 . <Имя объекта: 7ed57d00>) (333 . <Имя объекта: 7ed57ce8>) 
(333 . <Имя объекта: 7ed57cf0>) (333 . <Имя объекта: 7ed57cd0>) (333 . <Имя объекта: 7ed57ce0>) (333 . <Имя объекта: 7ed57cd8>) 
(333 . <Имя объекта: 7ed57cc0>) (333 . <Имя объекта: 7ed57cc8>) (333 . <Имя объекта: 7ed57cb8>))
