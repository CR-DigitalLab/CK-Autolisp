; C:COGO
;
; Record coordinate geometry points from AcadCAD into a text based cogo file.
; Allows user to select points (c:p), adds a description and places a point 
; number on the draiwing.  User can also select and set elevation (c:pe) and
; print a table of cogo coordinates (c:cogotable)
;
; By: Jason A. Cox
;
(setq cogofilename nil)
(setq cogooffset 5.0)
(setq cogoptcolor "WHITE")
(setq cogotextcolor "WHITE")

; function to return filename for current drawing w/o DWG suffix
(defun dwgfname ( / start prefix name)
        (cond
        ((= (getvar "acadver") "14.0")
                ; strip postfix
                (strcat layerdir
                     (substr (getvar "dwgname") 1 (- (strlen (getvar "dwgname")) 4))
                )

        )
        (t
                ; strip drive and directory and prefix with layerdir
                (setq prefix (getvar "dwgprefix"))
                (setq start (strlen prefix))
                (if (= prefix (substr (getvar "dwgname") 1 (strlen prefix)))
                        (strcat layerdir (substr (getvar "dwgname") (+ start 1)))
                        (strcat layerdir (getvar "dwgname"))
                )
        )
        )
)

; utility function
(defun filen (n / a b)
	(setq a (strlen n))
	(while (and (> a 0) (/= (substr n a 1) "\\"))
		(setq a (- a 1))
	)
	(setq a (+ 1 a))
	(setq b (substr n a))
)

(defun cogoinitfile ( / f fn)
	(prompt "\nSurvey3 Data File Routine -- Initializing\n")
	(setq fn (getstring (strcat "Enter Point Data Filename (no extension) <"
                        (strcat "Z:\\" (filen (strcat (dwgfname))))
			">: ")
		  )
	)
        (setq cogofilename (if (= fn "") (strcat "Z:\\" (filen (dwgfname))) fn))
	(setq fn (getstring (strcat "Enter Point Color <"
			cogoptcolor
			">: ")
		  )
	)
	(setq cogoptcolor (if (= fn "") cogoptcolor fn))
	(setq fn (getstring (strcat "Enter Text Color <"
			cogotextcolor
			">: ")
		  )
	)
	(setq cogotextcolor (if (= fn "") cogotextcolor fn))
	(setq cogooffset (getreal "Enter Text Offset Distance: "))
	(setq cogopointnum
		(if (null (setq f (open (strcat cogofilename ".asc") "r"))) 
			1
			(+ 1 (maxpointloader f))
		)
	)
	(setq cogopointnum2
		(if (null (setq f (open (strcat cogofilename ".num") "r"))) 
			0
			(+ 0 (read (read-line f)))
		)
	)
	(if f (close f) nil)
	(setq num (getint (strcat "Highest point number is "
		(itoa (- cogopointnum 1)) 
		" and last point entered was "
		(itoa cogopointnum2)
		"\r\nEnter new point number <"
	       (itoa cogopointnum)
	       ">: ")
	 )
	)
	(setq cogopointnum (- (if num num cogopointnum) 1))
	(setq f (getstring "Print Northing & Easting on Plan? (Y/N): "))
	(setq cogoprint (or (= "Y" f) (= "y" f)))
       
	(prompt "Initialized.\n")
)

(defun c:p ( / pt tmp desc num f i p2 NORTH EAST)
	(prompt "\nSurvey3 Data File Routine -- Add Point\n")
	(while (null (setq pt (getpoint "Pick point: "))))
	(setq cogopointnum (+ cogopointnum 1))
	(prompt (strcat "Point number: " (itoa cogopointnum) "\n"))
	(setq desc (getstring T "Enter point Description: "))
	(setq f (open (strcat cogofilename ".num") "w"))
	(princ cogopointnum f)
	(close f)
	(setq f (open (strcat cogofilename ".asc") "a"))
	(write-line (strcat (itoa cogopointnum) "," (rtos (cadr pt) 2 8) "," (rtos (car pt) 2 8) "," (rtos (caddr pt) 2 8) "," desc) f)
	(close f)
	(setq EAST (strcat "E:" (rtos (car pt) 2 4)))
	(setq NORTH (strcat "N:" (rtos (cadr pt) 2 4)))
	(command "color" cogoptcolor)
	(command "point" pt)
	(command "color" cogotextcolor)
	(setq desc (strcat " " (itoa cogopointnum)))
	(setq p2 (strcat (rtos (+ (car pt) cogooffset)) "," (rtos (+ (cadr pt) cogooffset))))
	(command "text" p2 "<<0" desc)
	(if cogoprint (command "text" "" NORTH) nil)
	(if cogoprint (command "text" "" EAST) nil)
	(setq i (strcat "N:" (rtos (cadr pt) 2 8) "  E:" (rtos (car pt) 2 8)))
	(prompt i)
	(princ)
)


(defun c:pe ( / pt tmp num f i p2 NORTH EAST elev desc)
	(prompt "\nSurvey3 Data File Routine -- Add Point with Elevation\n")
	(while (null (setq pt (getpoint "Pick point: "))))
	(setq cogopointnum (+ cogopointnum 1))
	(prompt (strcat "Point number: " (itoa cogopointnum) "\n"))
	(setq desc (getstring T "Enter point Description: "))
	(setq elev (getreal "Enter point Elevation: "))
	(setq f (open (strcat cogofilename ".num") "w"))
	(princ cogopointnum f)
	(close f)
	(setq f (open (strcat cogofilename ".asc") "a"))
	(write-line (strcat (itoa cogopointnum) "," (rtos (cadr pt) 2 8) "," (rtos (car pt) 2 8) "," (rtos elev 2 8) "," desc) f)
	(close f)
	(setq EAST (strcat "E:" (rtos (car pt) 2 4)))
	(setq NORTH (strcat "N:" (rtos (cadr pt) 2 4)))
	(command "color" cogoptcolor)
	(command "point" pt)
	(command "color" cogotextcolor)
	(setq desc (strcat " " (itoa cogopointnum)))
	(setq p2 (strcat (rtos (+ (car pt) cogooffset)) "," (rtos (+ (cadr pt) cogooffset))))
	(command "text" p2 "<<0" desc)
	(if cogoprint (command "text" "" NORTH) nil)
	(if cogoprint (command "text" "" EAST) nil)
	(setq i (strcat "N:" (rtos (cadr pt) 2 8) "  E:" (rtos (car pt) 2 8)))
	(prompt i)
	(princ)
)

(defun c:peg ( / pt tmp num f i p2 NORTH EAST elev desc)
	(prompt "\nSurvey3 Data File Routine -- Add Point with Elevation\n")
	(while (null (setq pt (getpoint "Pick point: "))))
	(setq cogopointnum (+ cogopointnum 1))
	(prompt (strcat "Point number: " (itoa cogopointnum) "\n"))
        (setq desc "GRADING")
	(setq elev (getreal "Enter point Elevation: "))
	(setq f (open (strcat cogofilename ".num") "w"))
	(princ cogopointnum f)
	(close f)
	(setq f (open (strcat cogofilename ".asc") "a"))
	(write-line (strcat (itoa cogopointnum) "," (rtos (cadr pt) 2 8) "," (rtos (car pt) 2 8) "," (rtos elev 2 8) "," desc) f)
	(close f)
	(setq EAST (strcat "E:" (rtos (car pt) 2 4)))
	(setq NORTH (strcat "N:" (rtos (cadr pt) 2 4)))
	(command "color" cogoptcolor)
	(command "point" pt)
	(command "color" cogotextcolor)
	(setq desc (strcat " " (itoa cogopointnum)))
	(setq p2 (strcat (rtos (+ (car pt) cogooffset)) "," (rtos (+ (cadr pt) cogooffset))))
	(command "text" p2 "<<0" desc)
	(if cogoprint (command "text" "" NORTH) nil)
	(if cogoprint (command "text" "" EAST) nil)
	(setq i (strcat "N:" (rtos (cadr pt) 2 8) "  E:" (rtos (car pt) 2 8)))
	(prompt i)
	(princ)
)

(defun c:cogotable ( / pt f info)
	(prompt "Cogo Data Routine - Import Cogo Data")
	(setq pt (getpoint "Enter insertion point: "))
	(setq f (open (strcat cogofilename ".asc") "r"))
	(setq info (creader f))
	(close f)
	(prompt "DONE!")
	(princ)
)

(defun creader ( f / a b )
	(while (setq b (read-line f))
		(command "text" "" b)
	)
)

(defun maxpointloader (f / a ret ptn pt fn)
	(setq ret '0)
        (while (setq a (read-line f))
		(setq ptn (atoi (car (pointfirstval a))))
		(prompt (strcat (car (pointfirstval a))  "\r"))
		(setq ret (if (> ptn ret) ptn ret))
        )
        (prompt "DONE\r\n");
        (close f)
        (setq a ret)
)
(defun pointreader (a / a b pt north east elev)
        (setq b (pointfirstval a))
        (setq pt (atoi (car b)))
        (setq b (pointfirstval (cadr b)))
        (setq north (atof (car b)))
        (setq b (pointfirstval (cadr b)))
        (setq east (atof (car b)))
        (setq b (pointfirstval (cadr b)))
        (setq elev (atof (car b)))
        (list pt east north elev)
)
(defun pointfirstval (s / i j first second)
         (setq i 1)
	 (setq j 1)
         (while (and
                  (< j (strlen s))
                  (or
                        (= " " (substr s j 1))
                        (= "," (substr s j 1))
                  )
                )
                (setq j (+ j 1))
         )
         (setq i j)
         (while (and
                 (< i (strlen s))
                 (not (or (= " " (substr s i 1)) (= "," (substr s i 1)))))
                (setq i (+ i 1))
         )
         (setq first (substr s j (- i 1)))
         (while (and
                  (< i (strlen s))
                  (or
                        (= " " (substr s i 1))
                        (= "," (substr s i 1))
                  )
                )
                (setq i (+ i 1))
         )
         (setq second (substr s i))
         (list first second)
)


(cogoinitfile)
(princ)
