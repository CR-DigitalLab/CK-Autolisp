(defun c:ai_dim_textbelow (/ ss)
  (ai_sysvar '("cmdecho" . 0))
  (if (setq ss (ssget "_I"))
    (command "_.dimoverride" "_dimtad" 4 "" ss "")
    (if (setq ss (ssget))
      (command "_.dimoverride" "_dimtad" 4 "" ss "") 
    )
  )
  (ai_sysvar NIL)
  (princ)
)
