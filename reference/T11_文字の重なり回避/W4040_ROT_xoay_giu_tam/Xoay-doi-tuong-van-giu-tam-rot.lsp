(Defun c:rot ( )
(princ "\nPHAM QUOC DUY Binh Son - Quang ngai")
(command "undo" "be")
(Princ "\nHay chon doi tuong :")
(setq SS (ssget '((0 . "TEXT"))))

  (setq gqtTB (dnint "\nNhap goc xoay: "gqtTB1))
 (setq  gqtTB1 gqtTB)

(setq i 0)
(setq N (sslength ss))
(while (< i N)
  (setq TEXTENT (ssname SS i))
(setq luubatdiem (getvar "osmode"))
 (setvar "osmode" 0)
(command "ucs" "object" textent)
(setq tbTB (textbox (list (cons -1 textent)))
        ll (car tbTB)
       ur (cadr tbTB)
       ul (list (car ll) (cadr ur))
       lr (list (car ur) (cadr ll))
)

 (setq  daitext (distance ul lr))
 (setq goctext(angle ul lr))
 (setq dainuatext (/ daitext 2))
 (setq diemquay (polar ul goctext dainuatext))

(command ".rotate" textent "" diemquay gqtTB)
(command "ucs" "p")
  (setq i (1+ i))
(setvar "osmode" luubatdiem)
)
(command "undo" "end")
(setvar "MODEMACRO" "**CHUC BAN LAM VIEC HIEU QUA** PHAM QUOC DUY - BINH SON - QUANG NGAI")
     (Princ)
)
