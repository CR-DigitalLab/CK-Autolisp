; CAN CHINH TEXT, MTEXT THEO LE TRAI (JL), LE PHAI(JP), CAN GIUA(JC)
; CONG TY TNHH MTV XD LOC AN PHU
;=======================================================================
(defun c:JL( / ssl #sset pt temp ed new old theight)
  (setq os (getvar "OSMODE"))
  (command ".undo" "BE")
  (command ".UCS" "W" ^C^C)
  (prompt "\nCh\U+1ECDn TEXT c\U+1EA7n ch\U+1EC9nh s\U+1EEDa: ")
  (setq #sset (ssget '((0 . "TEXT"))))  
  (setq ssl (sslength #sset))
  (setq pcanh (getpoint "\n diem canh: "))
  (while (> ssl 0)
    (setq te (ssname #sset (setq ssl (1- ssl))))
    (setq pt (cdr (assoc 11 (entget te))))
    (if (equal pt '(0.0 0.0 0.0))
      (setq pt (cdr (assoc 10 (entget te))))
    )
    (setq ptnew (list (car pcanh) (cadr pt) 0.0))
    (setq tent (entget te))
    (setq tent (subst (cons 73 2) (assoc 73 tent) tent))
    (setq tent (subst (cons 72 0) (assoc 72 tent) tent))
    (setq tent (subst (cons 11 ptnew) (assoc 11 tent) tent))
    (entmod tent)
  )
  (command ".undo" "E")
  (princ)
  (princ)
)
;======================================================================================================================================================================
(defun c:JR( / ssl #sset pt temp ed new old theight)
  (setq os (getvar "OSMODE"))
  (command ".undo" "BE")
  (command ".UCS" "W" ^C^C)
  (prompt "\nCh\U+1ECDn TEXT c\U+1EA7n ch\U+1EC9nh s\U+1EEDa: ")
  (setq #sset (ssget '((0 . "TEXT"))))  
  (setq ssl (sslength #sset))
  (setq pcanh (getpoint "\n diem canh: "))
  (while (> ssl 0)
    (setq te (ssname #sset (setq ssl (1- ssl))))
    (setq pt (cdr (assoc 11 (entget te))))
    (if (equal pt '(0.0 0.0 0.0))
      (setq pt (cdr (assoc 10 (entget te))))
    )
    (setq ptnew (list (car pcanh) (cadr pt) 0.0))
    (setq tent (entget te))
    (setq tent (subst (cons 73 2) (assoc 73 tent) tent))
    (setq tent (subst (cons 72 2) (assoc 72 tent) tent))
    (setq tent (subst (cons 11 ptnew) (assoc 11 tent) tent))
    (entmod tent)
  )
  (command ".undo" "E")
  (princ)
  (princ)
)
;======================================================================================================================================================================
(defun c:JC( / ssl #sset pt temp ed new old theight)
  (setq os (getvar "OSMODE"))
  (command ".undo" "BE")
  (command ".UCS" "W" ^C^C)
  (prompt "\nCh\U+1ECDn TEXT c\U+1EA7n ch\U+1EC9nh s\U+1EEDa: ")
  (setq #sset (ssget '((0 . "TEXT"))))  
  (setq ssl (sslength #sset))
  (setq pcanh (getpoint "\nCh\U+1ECDn \U+0111i\U+1EC3m canh: "))
  (while (> ssl 0)
    (setq te (ssname #sset (setq ssl (1- ssl))))
    (setq pt (cdr (assoc 11 (entget te))))
    (if (equal pt '(0.0 0.0 0.0))
      (setq pt (cdr (assoc 10 (entget te))))
    )
    (setq ptnew (list (car pcanh) (cadr pt) 0.0))
    (setq tent (entget te))
    (setq tent (subst (cons 73 2) (assoc 73 tent) tent))
    (setq tent (subst (cons 72 1) (assoc 72 tent) tent))
    (setq tent (subst (cons 11 ptnew) (assoc 11 tent) tent))
    (entmod tent)
  )
  (command ".undo" "E")
  (princ)
  (princ)
)
