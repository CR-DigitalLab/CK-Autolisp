(defun rt_hata (s)
  (if (/= s "Function cancelled")
    (princ (strcat "
Error: " s))
  )
  (setq *error* olderr)               
(princ))
(defun rt_uygula ()
  (setq rt_sec_say (sslength rt_sec))
  (setq c 0)
  (while (> rt_sec_say c)
    (setq e_rt_sec (ssname rt_sec c))
    (setq ee_rt_sec (entget e_rt_sec))
    (setq ee_rt_sec (append ee_rt_sec (list (cons 50 secim_aci))))
    (entmod ee_rt_sec)
    (setq c (+ c 1))
    (setq rt_e t)
  )
)
(defun c:rty ()
(prompt "[cizimokulu.com]")
(setq olderr *error*
      *error* rt_hata)
  (setq
    rt_sec (ssget
     '((-4 . "<OR") (0 . "TEXT") (0 . "MTEXT") (-4 . "OR>"))
   )
  )
  (if (= rt_sec nil)
    (progn
      (princ)
    )
    (progn
      (setq rt_e nil)
      (setvar "errno" 0)
      (while (= rt_e nil)
(setq rt_ent (entsel "
Referans nesneyi seçiniz:"))
(if (= rt_ent nil)
  (progn
    (if	(= (getvar "errno") 7)
      (progn
(setq rt_e nil)
(setvar "errno" 0)
      )
    )
    (if	(= (getvar "errno") 52)
      (progn (setq rt_e t) (setvar "errno" 0))
    )
  )
  (progn
    (command "select" rt_sec "")
    (setq rt_ent_tan (cdr (assoc 0 (entget (car rt_ent)))))
    (if	(and (/= rt_ent_tan "LINE")
     (/= rt_ent_tan "XLINE")
     (/= rt_ent_tan "RAY")
     (/= rt_ent_tan "TEXT")
)
      (progn
(princ
  "
Bu komut seçtiğiniz nesne türü için geçerli değildir..."
)
(setq rt_e t)
      )
    )
    (if	(= rt_ent_tan "TEXT")
      (progn
(setq secim_aci (cdr (assoc 50 (entget (car rt_ent)))))
(rt_uygula)
      )
    )
    (if	(or (= rt_ent_tan "LINE")
    (= rt_ent_tan "XLINE")
    (= rt_ent_tan "RAY")
)
      (progn
(setq secim_bas	(cdr (assoc 10 (entget (car rt_ent))))
      secim_son	(cdr (assoc 11 (entget (car rt_ent))))
)
(setq secim_aci (angle secim_bas secim_son))
(if (and (> secim_aci (angtof "0.0000"))
(< secim_aci (angtof "90.0000"))
    )
  (setq secim_aci secim_aci)
)
(if (and (> secim_aci (angtof "91.0000"))
(< secim_aci (angtof "180.0000"))
    )
  (setq secim_aci (+ secim_aci (angtof "180.0000")))
)
(if (and (> secim_aci (angtof "181.0000"))
(< secim_aci (angtof "270.0000"))
    )
  (setq secim_aci (+ secim_aci (angtof "180.0000")))
)
(if (and (> secim_aci (angtof "271.0000"))
(< secim_aci (angtof "360.0000"))
    )
  (setq secim_aci secim_aci)
)
(rt_uygula)
(setq rt_e t)
      )
    )
  )
)
      )
    )
  )
  (princ)
)
(princ)(PRINC " --> 'cizimokulu.com' Çizim yardımları yüklendi !")
