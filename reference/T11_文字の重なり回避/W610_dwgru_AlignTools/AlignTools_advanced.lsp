; ============================================
; ALIGNTOOLS_ADVANCED.LSP - Команды выравнивания и распределения
; ============================================


; Основная команда для вызова диалогового окна
(defun c:ALIGNTOOLS (/ dcl_id)
    (setq dcl_id (load_dialog "AlignTools_advanced.dcl"))
    
    (if (not (new_dialog "align_tools" dcl_id))
        (progn
            (princ "\nОшибка загрузки диалогового окна!")
            (unload_dialog dcl_id)
            (exit)
        )
    )
    
    ; Назначение действий для кнопок
    (action_tile "al" "(done_dialog 1)")
    (action_tile "ar" "(done_dialog 2)")
    (action_tile "at" "(done_dialog 3)")
    (action_tile "ab" "(done_dialog 4)")
    (action_tile "acx" "(done_dialog 5)")
    (action_tile "acy" "(done_dialog 6)")

    (action_tile "rlx" "(done_dialog 7)")
    (action_tile "rrx" "(done_dialog 8)")
    (action_tile "rty" "(done_dialog 9)")
    (action_tile "rby" "(done_dialog 10)")
    (action_tile "rcx" "(done_dialog 11)")
    (action_tile "rcy" "(done_dialog 12)")
    (action_tile "rzx" "(done_dialog 13)")
    (action_tile "rzy" "(done_dialog 14)")

    (action_tile "rlxd" "(done_dialog 15)")
    (action_tile "rrxd" "(done_dialog 16)")
    (action_tile "rtyd" "(done_dialog 17)")
    (action_tile "rbyd" "(done_dialog 18)")
    (action_tile "rcxd" "(done_dialog 19)")
    (action_tile "rcyd" "(done_dialog 20)")
    (action_tile "rzxd" "(done_dialog 21)")
    (action_tile "rzyd" "(done_dialog 22)")
    
    (action_tile "accept" "(done_dialog 23)")
    (action_tile "cancel" "(done_dialog 0)")
    
    (setq result (start_dialog))
    (unload_dialog dcl_id)
    
    ; Вызов соответствующей команды в зависимости от результата
    (cond
        ((= result 1) (c:AL))
        ((= result 2) (c:AR))
        ((= result 3) (c:AT))
        ((= result 4) (c:AB))
        ((= result 5) (c:ACX))
        ((= result 6) (c:ACY))
		
        ((= result 7) (c:RLX))
        ((= result 8) (c:RRX))
        ((= result 9) (c:RTY))
        ((= result 10) (c:RBY))
        ((= result 11) (c:RCX))
        ((= result 12) (c:RCY))
        ((= result 13) (c:RZX))
        ((= result 14) (c:RZY))
		
        ((= result 15) (c:RLXD))
        ((= result 16) (c:RRXD))
        ((= result 17) (c:RTYD))
        ((= result 18) (c:RBYD))
        ((= result 19) (c:RCXD))
        ((= result 20) (c:RCYD))
        ((= result 21) (c:RZXD))
        ((= result 22) (c:RZYD))
		
        ((= result 23) (princ "\nДиалог закрыт"))
        ((= result 0) (princ "\nОтменено"))
    )
    (princ)
)

; Команда быстрого доступа (короткое имя)
(defun c:ATOOLS ()
    (c:ALIGNTOOLS)
)

; ============================================
; ВСПОМОГАТЕЛЬНЫЕ ФУНКЦИИ
; ============================================

; Функция для получения bounding box объекта
(defun getBoundingBox (ent / minPoint maxPoint)
    (if (and ent (entget ent))
        (progn
            (vla-getboundingbox (vlax-ename->vla-object ent) 'minPoint 'maxPoint)
            (list
                (vlax-safearray->list minPoint)
                (vlax-safearray->list maxPoint)
            )
        )
    )
)

; ============================================
; ФУНКЦИИ ВЫРАВНИВАНИЯ (6 функций)
; ============================================

(defun c:AL (/ ss i ent minX boundingBox leftPt deltaX)
    (princ "\nВыберите объекты для выравнивания по левому краю: ")
    (setq ss (ssget))
    (if ss
        (progn
            (vl-load-com)
            (setq minX 1e308)
            (setq i 0)
            (while (< i (sslength ss))
                (setq ent (ssname ss i))
                (setq boundingBox (getBoundingBox ent))
                (if boundingBox
                    (progn
                        (setq leftPt (car boundingBox))
                        (if (< (car leftPt) minX) (setq minX (car leftPt)))
                    )
                )
                (setq i (1+ i))
            )
            (command "_.UNDO" "_Begin")
            (setq i 0)
            (while (< i (sslength ss))
                (setq ent (ssname ss i))
                (setq boundingBox (getBoundingBox ent))
                (if boundingBox
                    (progn
                        (setq leftPt (car boundingBox))
                        (setq deltaX (- minX (car leftPt)))
                        (if (not (equal deltaX 0.0 1e-8))
                            (command "._MOVE" ent "" "0,0" (list deltaX 0.0 0.0))
                        )
                    )
                )
                (setq i (1+ i))
            )
            (command "_.UNDO" "_End")
            (princ (strcat "\nВыровнено объектов по левому краю: " (itoa (sslength ss))))
            (sssetfirst nil ss)
        )
        (princ "\nОбъекты не выбраны.")
    )
    (princ)
)

(defun c:AR (/ ss i ent maxX boundingBox rightPt deltaX)
    (princ "\nВыберите объекты для выравнивания по правому краю: ")
    (setq ss (ssget))
    (if ss
        (progn
            (vl-load-com)
            (setq maxX -1e308)
            (setq i 0)
            (while (< i (sslength ss))
                (setq ent (ssname ss i))
                (setq boundingBox (getBoundingBox ent))
                (if boundingBox
                    (progn
                        (setq rightPt (cadr boundingBox))
                        (if (> (car rightPt) maxX) (setq maxX (car rightPt)))
                    )
                )
                (setq i (1+ i))
            )
            (command "_.UNDO" "_Begin")
            (setq i 0)
            (while (< i (sslength ss))
                (setq ent (ssname ss i))
                (setq boundingBox (getBoundingBox ent))
                (if boundingBox
                    (progn
                        (setq rightPt (cadr boundingBox))
                        (setq deltaX (- maxX (car rightPt)))
                        (if (not (equal deltaX 0.0 1e-8))
                            (command "._MOVE" ent "" "0,0" (list deltaX 0.0 0.0))
                        )
                    )
                )
                (setq i (1+ i))
            )
            (command "_.UNDO" "_End")
            (princ (strcat "\nВыровнено объектов по правому краю: " (itoa (sslength ss))))
            (sssetfirst nil ss)
        )
        (princ "\nОбъекты не выбраны.")
    )
    (princ)
)

(defun c:AT (/ ss i ent maxY boundingBox topPt deltaY)
    (princ "\nВыберите объекты для выравнивания по верхнему краю: ")
    (setq ss (ssget))
    (if ss
        (progn
            (vl-load-com)
            (setq maxY -1e308)
            (setq i 0)
            (while (< i (sslength ss))
                (setq ent (ssname ss i))
                (setq boundingBox (getBoundingBox ent))
                (if boundingBox
                    (progn
                        (setq topPt (cadr boundingBox))
                        (if (> (cadr topPt) maxY) (setq maxY (cadr topPt)))
                    )
                )
                (setq i (1+ i))
            )
            (command "_.UNDO" "_Begin")
            (setq i 0)
            (while (< i (sslength ss))
                (setq ent (ssname ss i))
                (setq boundingBox (getBoundingBox ent))
                (if boundingBox
                    (progn
                        (setq topPt (cadr boundingBox))
                        (setq deltaY (- maxY (cadr topPt)))
                        (if (not (equal deltaY 0.0 1e-8))
                            (command "._MOVE" ent "" "0,0" (list 0.0 deltaY 0.0))
                        )
                    )
                )
                (setq i (1+ i))
            )
            (command "_.UNDO" "_End")
            (princ (strcat "\nВыровнено объектов по верхнему краю: " (itoa (sslength ss))))
            (sssetfirst nil ss)
        )
        (princ "\nОбъекты не выбраны.")
    )
    (princ)
)

(defun c:AB (/ ss i ent minY boundingBox bottomPt deltaY)
    (princ "\nВыберите объекты для выравнивания по нижнему краю: ")
    (setq ss (ssget))
    (if ss
        (progn
            (vl-load-com)
            (setq minY 1e308)
            (setq i 0)
            (while (< i (sslength ss))
                (setq ent (ssname ss i))
                (setq boundingBox (getBoundingBox ent))
                (if boundingBox
                    (progn
                        (setq bottomPt (car boundingBox))
                        (if (< (cadr bottomPt) minY) (setq minY (cadr bottomPt)))
                    )
                )
                (setq i (1+ i))
            )
            (command "_.UNDO" "_Begin")
            (setq i 0)
            (while (< i (sslength ss))
                (setq ent (ssname ss i))
                (setq boundingBox (getBoundingBox ent))
                (if boundingBox
                    (progn
                        (setq bottomPt (car boundingBox))
                        (setq deltaY (- minY (cadr bottomPt)))
                        (if (not (equal deltaY 0.0 1e-8))
                            (command "._MOVE" ent "" "0,0" (list 0.0 deltaY 0.0))
                        )
                    )
                )
                (setq i (1+ i))
            )
            (command "_.UNDO" "_End")
            (princ (strcat "\nВыровнено объектов по нижнему краю: " (itoa (sslength ss))))
            (sssetfirst nil ss)
        )
        (princ "\nОбъекты не выбраны.")
    )
    (princ)
)

(defun c:ACX (/ ss i ent boundingBoxList minX maxX centerX deltaX)
    (princ "\nВыберите объекты для выравнивания по центру (X): ")
    (setq ss (ssget))
    (if ss
        (progn
            (vl-load-com)
            (setq boundingBoxList '())
            (setq minX 1e308)
            (setq maxX -1e308)
            (setq i 0)
            (while (< i (sslength ss))
                (setq ent (ssname ss i))
                (setq boundingBox (getBoundingBox ent))
                (if boundingBox
                    (progn
                        (setq boundingBoxList (cons (list ent boundingBox) boundingBoxList))
                        (setq leftPt (car boundingBox))
                        (setq rightPt (cadr boundingBox))
                        (if (< (car leftPt) minX) (setq minX (car leftPt)))
                        (if (> (car rightPt) maxX) (setq maxX (car rightPt)))
                    )
                )
                (setq i (1+ i))
            )
            (command "_.UNDO" "_Begin")
            (setq centerX (/ (+ minX maxX) 2.0))
            (foreach item boundingBoxList
                (setq ent (car item))
                (setq boundingBox (cadr item))
                (setq objLeft (car (car boundingBox)))
                (setq objRight (car (cadr boundingBox)))
                (setq objCenterX (/ (+ objLeft objRight) 2.0))
                (setq deltaX (- centerX objCenterX))
                (if (not (equal deltaX 0.0 1e-8))
                    (command "._MOVE" ent "" "0,0" (list deltaX 0.0 0.0))
                )
            )
            (command "_.UNDO" "_End")
            (princ (strcat "\nВыровнено объектов по центру (X): " (itoa (length boundingBoxList))))
            (sssetfirst nil ss)
        )
        (princ "\nОбъекты не выбраны.")
    )
    (princ)
)

(defun c:ACY (/ ss i ent boundingBoxList minY maxY centerY deltaY)
    (princ "\nВыберите объекты для выравнивания по центру (Y): ")
    (setq ss (ssget))
    (if ss
        (progn
            (vl-load-com)
            (setq boundingBoxList '())
            (setq minY 1e308)
            (setq maxY -1e308)
            (setq i 0)
            (while (< i (sslength ss))
                (setq ent (ssname ss i))
                (setq boundingBox (getBoundingBox ent))
                (if boundingBox
                    (progn
                        (setq boundingBoxList (cons (list ent boundingBox) boundingBoxList))
                        (setq bottomPt (car boundingBox))
                        (setq topPt (cadr boundingBox))
                        (if (< (cadr bottomPt) minY) (setq minY (cadr bottomPt)))
                        (if (> (cadr topPt) maxY) (setq maxY (cadr topPt)))
                    )
                )
                (setq i (1+ i))
            )
            (command "_.UNDO" "_Begin")
            (setq centerY (/ (+ minY maxY) 2.0))
            (foreach item boundingBoxList
                (setq ent (car item))
                (setq boundingBox (cadr item))
                (setq objBottom (cadr (car boundingBox)))
                (setq objTop (cadr (cadr boundingBox)))
                (setq objCenterY (/ (+ objBottom objTop) 2.0))
                (setq deltaY (- centerY objCenterY))
                (if (not (equal deltaY 0.0 1e-8))
                    (command "._MOVE" ent "" "0,0" (list 0.0 deltaY 0.0))
                )
            )
            (command "_.UNDO" "_End")
            (princ (strcat "\nВыровнено объектов по центру (Y): " (itoa (length boundingBoxList))))
            (sssetfirst nil ss)
        )
        (princ "\nОбъекты не выбраны.")
    )
    (princ)
)

; ============================================
; ФУНКЦИИ РАСПРЕДЕЛЕНИЯ (АВТОМАТИЧЕСКИЕ - 8 функций)
; ============================================

(defun c:RLX (/ ss count objects sortedObjects leftObj rightObj minX maxX totalWidth spacing currentX i obj boundingBox leftPt)
    (princ "\nВыберите объекты для распределения по горизонтали (левый край): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq leftPt (car boundingBox))
                        (setq objects (cons (list ent leftPt (car leftPt)) objects))
                    )
                )
                (setq i (1+ i))
            )
            (setq sortedObjects (vl-sort objects '(lambda (a b) (< (caddr a) (caddr b)))))
            (setq leftObj (car sortedObjects))
            (setq rightObj (last sortedObjects))
            (setq minX (caddr leftObj))
            (setq maxX (caddr rightObj))
            (setq totalWidth (- maxX minX))
            (setq spacing (/ totalWidth (1- count)))
            (command "_.UNDO" "_Begin")
            (setq i 0)
            (foreach obj sortedObjects
                (if (and (/= i 0) (/= i (1- count)))
                    (progn
                        (setq targetX (+ minX (* spacing i)))
                        (setq currentX (caddr obj))
                        (setq deltaX (- targetX currentX))
                        (if (not (equal deltaX 0.0 1e-8))
                            (command "._MOVE" (car obj) "" "0,0" (list deltaX 0.0 0.0))
                        )
                    )
                )
                (setq i (1+ i))
            )
            (command "_.UNDO" "_End")
            (princ (strcat "\nРаспределено объектов по горизонтали: " (itoa count)))
            (sssetfirst nil ss)
        )
        (if ss
            (princ "\nДля распределения нужно выбрать как минимум 3 объекта.")
            (princ "\nОбъекты не выбраны.")
        )
    )
    (princ)
)

(defun c:RRX (/ ss count objects sortedObjects leftObj rightObj minX maxX totalWidth spacing currentX i obj boundingBox rightPt)
    (princ "\nВыберите объекты для распределения по горизонтали (правый край): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq rightPt (cadr boundingBox))
                        (setq objects (cons (list ent rightPt (car rightPt)) objects))
                    )
                )
                (setq i (1+ i))
            )
            (setq sortedObjects (vl-sort objects '(lambda (a b) (< (caddr a) (caddr b)))))
            (setq leftObj (car sortedObjects))
            (setq rightObj (last sortedObjects))
            (setq minX (caddr leftObj))
            (setq maxX (caddr rightObj))
            (setq totalWidth (- maxX minX))
            (setq spacing (/ totalWidth (1- count)))
            (command "_.UNDO" "_Begin")
            (setq i 0)
            (foreach obj sortedObjects
                (if (and (/= i 0) (/= i (1- count)))
                    (progn
                        (setq targetX (+ minX (* spacing i)))
                        (setq currentX (caddr obj))
                        (setq deltaX (- targetX currentX))
                        (if (not (equal deltaX 0.0 1e-8))
                            (command "._MOVE" (car obj) "" "0,0" (list deltaX 0.0 0.0))
                        )
                    )
                )
                (setq i (1+ i))
            )
            (command "_.UNDO" "_End")
            (princ (strcat "\nРаспределено объектов по горизонтали (правый край): " (itoa count)))
            (sssetfirst nil ss)
        )
        (if ss
            (princ "\nДля распределения нужно выбрать как минимум 3 объекта.")
            (princ "\nОбъекты не выбраны.")
        )
    )
    (princ)
)

(defun c:RTY (/ ss count objects sortedObjects bottomObj topObj minY maxY totalHeight spacing currentY i obj boundingBox topPt)
    (princ "\nВыберите объекты для распределения по вертикали (верхний край): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq topPt (cadr boundingBox))
                        (setq objects (cons (list ent topPt (cadr topPt)) objects))
                    )
                )
                (setq i (1+ i))
            )
            (setq sortedObjects (vl-sort objects '(lambda (a b) (< (caddr a) (caddr b)))))
            (setq bottomObj (car sortedObjects))
            (setq topObj (last sortedObjects))
            (setq minY (caddr bottomObj))
            (setq maxY (caddr topObj))
            (setq totalHeight (- maxY minY))
            (setq spacing (/ totalHeight (1- count)))
            (command "_.UNDO" "_Begin")
            (setq i 0)
            (foreach obj sortedObjects
                (if (and (/= i 0) (/= i (1- count)))
                    (progn
                        (setq targetY (+ minY (* spacing i)))
                        (setq currentY (caddr obj))
                        (setq deltaY (- targetY currentY))
                        (if (not (equal deltaY 0.0 1e-8))
                            (command "._MOVE" (car obj) "" "0,0" (list 0.0 deltaY 0.0))
                        )
                    )
                )
                (setq i (1+ i))
            )
            (command "_.UNDO" "_End")
            (princ (strcat "\nРаспределено объектов по вертикали (верхний край): " (itoa count)))
            (sssetfirst nil ss)
        )
        (if ss
            (princ "\nДля распределения нужно выбрать как минимум 3 объекта.")
            (princ "\nОбъекты не выбраны.")
        )
    )
    (princ)
)

(defun c:RBY (/ ss count objects sortedObjects bottomObj topObj minY maxY totalHeight spacing currentY i obj boundingBox bottomPt)
    (princ "\nВыберите объекты для распределения по вертикали (нижний край): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq bottomPt (car boundingBox))
                        (setq objects (cons (list ent bottomPt (cadr bottomPt)) objects))
                    )
                )
                (setq i (1+ i))
            )
            (setq sortedObjects (vl-sort objects '(lambda (a b) (< (caddr a) (caddr b)))))
            (setq bottomObj (car sortedObjects))
            (setq topObj (last sortedObjects))
            (setq minY (caddr bottomObj))
            (setq maxY (caddr topObj))
            (setq totalHeight (- maxY minY))
            (setq spacing (/ totalHeight (1- count)))
            (command "_.UNDO" "_Begin")
            (setq i 0)
            (foreach obj sortedObjects
                (if (and (/= i 0) (/= i (1- count)))
                    (progn
                        (setq targetY (+ minY (* spacing i)))
                        (setq currentY (caddr obj))
                        (setq deltaY (- targetY currentY))
                        (if (not (equal deltaY 0.0 1e-8))
                            (command "._MOVE" (car obj) "" "0,0" (list 0.0 deltaY 0.0))
                        )
                    )
                )
                (setq i (1+ i))
            )
            (command "_.UNDO" "_End")
            (princ (strcat "\nРаспределено объектов по вертикали (нижний край): " (itoa count)))
            (sssetfirst nil ss)
        )
        (if ss
            (princ "\nДля распределения нужно выбрать как минимум 3 объекта.")
            (princ "\nОбъекты не выбраны.")
        )
    )
    (princ)
)

(defun c:RCX (/ ss count objects sortedObjects leftObj rightObj minCenterX maxCenterX totalWidth spacing currentCenterX i obj boundingBox centerX)
    (princ "\nВыберите объекты для распределения по горизонтали (по центрам): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq leftPt (car boundingBox))
                        (setq rightPt (cadr boundingBox))
                        (setq centerX (/ (+ (car leftPt) (car rightPt)) 2.0))
                        (setq objects (cons (list ent centerX) objects))
                    )
                )
                (setq i (1+ i))
            )
            (setq sortedObjects (vl-sort objects '(lambda (a b) (< (cadr a) (cadr b)))))
            (setq leftObj (car sortedObjects))
            (setq rightObj (last sortedObjects))
            (setq minCenterX (cadr leftObj))
            (setq maxCenterX (cadr rightObj))
            (setq totalWidth (- maxCenterX minCenterX))
            (setq spacing (/ totalWidth (1- count)))
            (command "_.UNDO" "_Begin")
            (setq i 0)
            (foreach obj sortedObjects
                (if (and (/= i 0) (/= i (1- count)))
                    (progn
                        (setq targetX (+ minCenterX (* spacing i)))
                        (setq currentCenterX (cadr obj))
                        (setq deltaX (- targetX currentCenterX))
                        (if (not (equal deltaX 0.0 1e-8))
                            (command "._MOVE" (car obj) "" "0,0" (list deltaX 0.0 0.0))
                        )
                    )
                )
                (setq i (1+ i))
            )
            (command "_.UNDO" "_End")
            (princ (strcat "\nРаспределено объектов по горизонтали (по центрам): " (itoa count)))
            (sssetfirst nil ss)
        )
        (if ss
            (princ "\nДля распределения нужно выбрать как минимум 3 объекта.")
            (princ "\nОбъекты не выбраны.")
        )
    )
    (princ)
)

(defun c:RCY (/ ss count objects sortedObjects bottomObj topObj minCenterY maxCenterY totalHeight spacing currentCenterY i obj boundingBox centerY)
    (princ "\nВыберите объекты для распределения по вертикали (по центрам): ")
    (setq ss (ssget))
    (if (and ss (> (sslength ss) 2))
        (progn
            (vl-load-com)
            (setq count (sslength ss))
            (setq objects '())
            (setq i 0)
            (while (< i count)
                (setq ent (ssname ss i))
                (setq boundingBox (getBoundingBox ent))
                (if boundingBox
                    (progn
                        (setq bottomPt (car boundingBox))
                        (setq topPt (cadr boundingBox))
                        (setq centerY (/ (+ (cadr bottomPt) (cadr topPt)) 2.0))
                        (setq objects (cons (list ent centerY) objects))
                    )
                )
                (setq i (1+ i))
            )
            (setq sortedObjects (vl-sort objects '(lambda (a b) (< (cadr a) (cadr b)))))
            (setq bottomObj (car sortedObjects))
            (setq topObj (last sortedObjects))
            (setq minCenterY (cadr bottomObj))
            (setq maxCenterY (cadr topObj))
            (setq totalHeight (- maxCenterY minCenterY))
            (setq spacing (/ totalHeight (1- count)))
            (command "_.UNDO" "_Begin")
            (setq i 0)
            (foreach obj sortedObjects
                (if (and (/= i 0) (/= i (1- count)))
                    (progn
                        (setq targetY (+ minCenterY (* spacing i)))
                        (setq currentCenterY (cadr obj))
                        (setq deltaY (- targetY currentCenterY))
                        (if (not (equal deltaY 0.0 1e-8))
                            (command "._MOVE" (car obj) "" "0,0" (list 0.0 deltaY 0.0))
                        )
                    )
                )
                (setq i (1+ i))
            )
            (command "_.UNDO" "_End")
            (princ (strcat "\nРаспределено объектов по вертикали (по центрам): " (itoa count)))
            (sssetfirst nil ss)
        )
        (if ss
            (princ "\nДля распределения нужно выбрать как минимум 3 объекта.")
            (princ "\nОбъекты не выбраны.")
        )
    )
    (princ)
)

(defun c:RZX (/ ss count objects sortedObjects minX maxX totalObjWidth gapWidth currentX i obj boundingBox leftPt rightPt objWidth)
    (princ "\nВыберите объекты для распределения по горизонтали (одинаковые промежутки): ")
    (setq ss (ssget))
    (if (and ss (> (sslength ss) 1))
        (progn
            (vl-load-com)
            (setq count (sslength ss))
            (setq objects '())
            (setq minX 1e308)
            (setq maxX -1e308)
            (setq i 0)
            (while (< i count)
                (setq ent (ssname ss i))
                (setq boundingBox (getBoundingBox ent))
                (if boundingBox
                    (progn
                        (setq leftPt (car boundingBox))
                        (setq rightPt (cadr boundingBox))
                        (setq objWidth (- (car rightPt) (car leftPt)))
                        (setq objects (cons (list ent (car leftPt) objWidth) objects))
                        (if (< (car leftPt) minX) (setq minX (car leftPt)))
                        (if (> (car rightPt) maxX) (setq maxX (car rightPt)))
                    )
                )
                (setq i (1+ i))
            )
            (setq sortedObjects (vl-sort objects '(lambda (a b) (< (cadr a) (cadr b)))))
            (setq totalObjWidth 0.0)
            (foreach obj sortedObjects
                (setq totalObjWidth (+ totalObjWidth (caddr obj)))
            )
            (setq totalSpace (- maxX minX))
            (setq gapWidth (/ (- totalSpace totalObjWidth) (1- count)))
            (command "_.UNDO" "_Begin")
            (setq currentX minX)
            (setq i 0)
            (foreach obj sortedObjects
                (setq targetX currentX)
                (setq deltaX (- targetX (cadr obj)))
                (if (not (equal deltaX 0.0 1e-8))
                    (command "._MOVE" (car obj) "" "0,0" (list deltaX 0.0 0.0))
                )
                (setq currentX (+ targetX (caddr obj) gapWidth))
                (setq i (1+ i))
            )
            (command "_.UNDO" "_End")
            (princ (strcat "\nРаспределено объектов по горизонтали (одинаковые промежутки): " (itoa count)))
            (sssetfirst nil ss)
        )
        (if ss
            (princ "\nДля распределения нужно выбрать как минимум 2 объекта.")
            (princ "\nОбъекты не выбраны.")
        )
    )
    (princ)
)

(defun c:RZY (/ ss count objects sortedObjects minY maxY totalObjHeight gapHeight currentY i obj boundingBox bottomPt topPt objHeight)
    (princ "\nВыберите объекты для распределения по вертикали (одинаковые промежутки): ")
    (setq ss (ssget))
    (if (and ss (> (sslength ss) 1))
        (progn
            (vl-load-com)
            (setq count (sslength ss))
            (setq objects '())
            (setq minY 1e308)
            (setq maxY -1e308)
            (setq i 0)
            (while (< i count)
                (setq ent (ssname ss i))
                (setq boundingBox (getBoundingBox ent))
                (if boundingBox
                    (progn
                        (setq bottomPt (car boundingBox))
                        (setq topPt (cadr boundingBox))
                        (setq objHeight (- (cadr topPt) (cadr bottomPt)))
                        (setq objects (cons (list ent (cadr bottomPt) objHeight) objects))
                        (if (< (cadr bottomPt) minY) (setq minY (cadr bottomPt)))
                        (if (> (cadr topPt) maxY) (setq maxY (cadr topPt)))
                    )
                )
                (setq i (1+ i))
            )
            (setq sortedObjects (vl-sort objects '(lambda (a b) (< (cadr a) (cadr b)))))
            (setq totalObjHeight 0.0)
            (foreach obj sortedObjects
                (setq totalObjHeight (+ totalObjHeight (caddr obj)))
            )
            (setq totalSpace (- maxY minY))
            (setq gapHeight (/ (- totalSpace totalObjHeight) (1- count)))
            (command "_.UNDO" "_Begin")
            (setq currentY minY)
            (setq i 0)
            (foreach obj sortedObjects
                (setq targetY currentY)
                (setq deltaY (- targetY (cadr obj)))
                (if (not (equal deltaY 0.0 1e-8))
                    (command "._MOVE" (car obj) "" "0,0" (list 0.0 deltaY 0.0))
                )
                (setq currentY (+ targetY (caddr obj) gapHeight))
                (setq i (1+ i))
            )
            (command "_.UNDO" "_End")
            (princ (strcat "\nРаспределено объектов по вертикали (одинаковые промежутки): " (itoa count)))
            (sssetfirst nil ss)
        )
        (if ss
            (princ "\nДля распределения нужно выбрать как минимум 2 объекта.")
            (princ "\nОбъекты не выбраны.")
        )
    )
    (princ)
)

; ============================================
; ФУНКЦИИ РАСПРЕДЕЛЕНИЯ (С РАССТОЯНИЕМ - 8 функций)
; ============================================


;; Глобальная переменная для хранения последнего расстояния
(if (not *rd-last-distance*)
    (setq *rd-last-distance* nil)  ; было 0.0
)


;; Вспомогательная функция для получения ограничивающей рамки
(defun getBoundingBox (ent / minPt maxPt)
    (vla-getboundingbox (vlax-ename->vla-object ent) 'minPt 'maxPt)
    (list (vlax-safearray->list minPt) (vlax-safearray->list maxPt))
)

;; Общая функция для запроса расстояния с сохранением (разрешены любые значения)
(defun get-distance-with-default (prompt / dist)
    (setq dist (getdist 
        (strcat prompt 
                (if (not (null *rd-last-distance*))
                    (strcat " <" (rtos *rd-last-distance*) ">: ")
                    ": ")
        )
    ))
    
    (if (null dist)
        (if (not (null *rd-last-distance*))
            (setq dist *rd-last-distance*)
            (progn
                (princ "\nСохраненное расстояние отсутствует. Укажите расстояние: ")
                (setq dist (getdist))
            )
        )
    )
    
    (if (not (null dist))
        (progn
            (setq *rd-last-distance* dist)
            dist
        )
        nil
    )
)

;; Распределение по горизонтали (левый край) с любым расстоянием
(defun c:RLXD (/ ss count objects sortedObjects distance currentX i obj boundingBox leftPt ent deltaX targetX)
    (princ "\nВыберите объекты для распределения по горизонтали (левый край): ")
    (setq ss (ssget))
    (if (and ss (> (sslength ss) 1))
        (progn
            (vl-load-com)
            (setq distance (get-distance-with-default "\nУкажите расстояние между левыми краями объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq leftPt (car boundingBox))
                                (setq objects (cons (list ent (car leftPt)) objects))
                            )
                        )
                        (setq i (1+ i))
                    )
                    (setq sortedObjects (vl-sort objects '(lambda (a b) (< (cadr a) (cadr b)))))
                    (command "_.UNDO" "_Begin")
                    (setq currentX (cadr (car sortedObjects)))
                    (setq i 0)
                    (foreach obj sortedObjects
                        (setq targetX currentX)
                        (setq deltaX (- targetX (cadr obj)))
                        (if (not (equal deltaX 0.0 1e-8))
                            (command "._MOVE" (car obj) "" "0,0" (list deltaX 0.0 0.0))
                        )
                        (setq currentX (+ targetX distance))
                        (setq i (1+ i))
                    )
                    (command "_.UNDO" "_End")
                    (princ (strcat "\nРаспределено объектов по левому краю с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по горизонтали (правый край) с любым расстоянием
(defun c:RRXD (/ ss count objects sortedObjects distance currentX i obj boundingBox rightPt ent deltaX targetX)
    (princ "\nВыберите объекты для распределения по горизонтали (правый край): ")
    (setq ss (ssget))
    (if (and ss (> (sslength ss) 1))
        (progn
            (vl-load-com)
            (setq distance (get-distance-with-default "\nУкажите расстояние между правыми краями объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq rightPt (cadr boundingBox))
                                (setq objects (cons (list ent (car rightPt)) objects))
                            )
                        )
                        (setq i (1+ i))
                    )
                    (setq sortedObjects (vl-sort objects '(lambda (a b) (< (cadr a) (cadr b)))))
                    (command "_.UNDO" "_Begin")
                    (setq currentX (cadr (car sortedObjects)))
                    (setq i 0)
                    (foreach obj sortedObjects
                        (setq targetX currentX)
                        (setq deltaX (- targetX (cadr obj)))
                        (if (not (equal deltaX 0.0 1e-8))
                            (command "._MOVE" (car obj) "" "0,0" (list deltaX 0.0 0.0))
                        )
                        (setq currentX (+ targetX distance))
                        (setq i (1+ i))
                    )
                    (command "_.UNDO" "_End")
                    (princ (strcat "\nРаспределено объектов по правому краю с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по вертикали (верхний край) с любым расстоянием
(defun c:RTYD (/ ss count objects sortedObjects distance currentY i obj boundingBox topPt ent deltaY targetY)
    (princ "\nВыберите объекты для распределения по вертикали (верхний край): ")
    (setq ss (ssget))
    (if (and ss (> (sslength ss) 1))
        (progn
            (vl-load-com)
            (setq distance (get-distance-with-default "\nУкажите расстояние между верхними краями объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq topPt (cadr boundingBox))
                                (setq objects (cons (list ent (cadr topPt)) objects))
                            )
                        )
                        (setq i (1+ i))
                    )
                    (setq sortedObjects (vl-sort objects '(lambda (a b) (< (cadr a) (cadr b)))))
                    (command "_.UNDO" "_Begin")
                    (setq currentY (cadr (car sortedObjects)))
                    (setq i 0)
                    (foreach obj sortedObjects
                        (setq targetY currentY)
                        (setq deltaY (- targetY (cadr obj)))
                        (if (not (equal deltaY 0.0 1e-8))
                            (command "._MOVE" (car obj) "" "0,0" (list 0.0 deltaY 0.0))
                        )
                        (setq currentY (+ targetY distance))
                        (setq i (1+ i))
                    )
                    (command "_.UNDO" "_End")
                    (princ (strcat "\nРаспределено объектов по верхнему краю с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по вертикали (нижний край) с любым расстоянием
(defun c:RBYD (/ ss count objects sortedObjects distance currentY i obj boundingBox bottomPt ent deltaY targetY)
    (princ "\nВыберите объекты для распределения по вертикали (нижний край): ")
    (setq ss (ssget))
    (if (and ss (> (sslength ss) 1))
        (progn
            (vl-load-com)
            (setq distance (get-distance-with-default "\nУкажите расстояние между нижними краями объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq bottomPt (car boundingBox))
                                (setq objects (cons (list ent (cadr bottomPt)) objects))
                            )
                        )
                        (setq i (1+ i))
                    )
                    (setq sortedObjects (vl-sort objects '(lambda (a b) (< (cadr a) (cadr b)))))
                    (command "_.UNDO" "_Begin")
                    (setq currentY (cadr (car sortedObjects)))
                    (setq i 0)
                    (foreach obj sortedObjects
                        (setq targetY currentY)
                        (setq deltaY (- targetY (cadr obj)))
                        (if (not (equal deltaY 0.0 1e-8))
                            (command "._MOVE" (car obj) "" "0,0" (list 0.0 deltaY 0.0))
                        )
                        (setq currentY (+ targetY distance))
                        (setq i (1+ i))
                    )
                    (command "_.UNDO" "_End")
                    (princ (strcat "\nРаспределено объектов по нижнему краю с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по горизонтали (по центрам) с любым расстоянием
(defun c:RCXD (/ ss count objects sortedObjects distance currentX i obj boundingBox leftPt rightPt centerX ent deltaX targetX)
    (princ "\nВыберите объекты для распределения по горизонтали (по центрам): ")
    (setq ss (ssget))
    (if (and ss (> (sslength ss) 1))
        (progn
            (vl-load-com)
            (setq distance (get-distance-with-default "\nУкажите расстояние между центрами объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq leftPt (car boundingBox))
                                (setq rightPt (cadr boundingBox))
                                (setq centerX (/ (+ (car leftPt) (car rightPt)) 2.0))
                                (setq objects (cons (list ent centerX) objects))
                            )
                        )
                        (setq i (1+ i))
                    )
                    (setq sortedObjects (vl-sort objects '(lambda (a b) (< (cadr a) (cadr b)))))
                    (command "_.UNDO" "_Begin")
                    (setq currentX (cadr (car sortedObjects)))
                    (setq i 0)
                    (foreach obj sortedObjects
                        (setq targetX currentX)
                        (setq deltaX (- targetX (cadr obj)))
                        (if (not (equal deltaX 0.0 1e-8))
                            (command "._MOVE" (car obj) "" "0,0" (list deltaX 0.0 0.0))
                        )
                        (setq currentX (+ targetX distance))
                        (setq i (1+ i))
                    )
                    (command "_.UNDO" "_End")
                    (princ (strcat "\nРаспределено объектов по центрам по горизонтали с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по вертикали (по центрам) с любым расстоянием
(defun c:RCYD (/ ss count objects sortedObjects distance currentY i obj boundingBox bottomPt topPt centerY ent deltaY targetY)
    (princ "\nВыберите объекты для распределения по вертикали (по центрам): ")
    (setq ss (ssget))
    (if (and ss (> (sslength ss) 1))
        (progn
            (vl-load-com)
            (setq distance (get-distance-with-default "\nУкажите расстояние между центрами объектов (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq bottomPt (car boundingBox))
                                (setq topPt (cadr boundingBox))
                                (setq centerY (/ (+ (cadr bottomPt) (cadr topPt)) 2.0))
                                (setq objects (cons (list ent centerY) objects))
                            )
                        )
                        (setq i (1+ i))
                    )
                    (setq sortedObjects (vl-sort objects '(lambda (a b) (< (cadr a) (cadr b)))))
                    (command "_.UNDO" "_Begin")
                    (setq currentY (cadr (car sortedObjects)))
                    (setq i 0)
                    (foreach obj sortedObjects
                        (setq targetY currentY)
                        (setq deltaY (- targetY (cadr obj)))
                        (if (not (equal deltaY 0.0 1e-8))
                            (command "._MOVE" (car obj) "" "0,0" (list 0.0 deltaY 0.0))
                        )
                        (setq currentY (+ targetY distance))
                        (setq i (1+ i))
                    )
                    (command "_.UNDO" "_End")
                    (princ (strcat "\nРаспределено объектов по центрам по вертикали с расстоянием " (rtos distance) ": " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по горизонтали (одинаковые промежутки) с любым расстоянием
(defun c:RZXD (/ ss count objects sortedObjects distance currentX i obj boundingBox leftPt rightPt objWidth ent deltaX targetX)
    (princ "\nВыберите объекты для распределения по горизонтали (одинаковые промежутки): ")
    (setq ss (ssget))
    (if (and ss (> (sslength ss) 1))
        (progn
            (vl-load-com)
            (setq distance (get-distance-with-default "\nУкажите расстояние между объектами (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq leftPt (car boundingBox))
                                (setq rightPt (cadr boundingBox))
                                (setq objWidth (- (car rightPt) (car leftPt)))
                                (setq objects (cons (list ent (car leftPt) objWidth) objects))
                            )
                        )
                        (setq i (1+ i))
                    )
                    (setq sortedObjects (vl-sort objects '(lambda (a b) (< (cadr a) (cadr b)))))
                    (command "_.UNDO" "_Begin")
                    (setq currentX (cadr (car sortedObjects)))
                    (setq i 0)
                    (foreach obj sortedObjects
                        (setq targetX currentX)
                        (setq deltaX (- targetX (cadr obj)))
                        (if (not (equal deltaX 0.0 1e-8))
                            (command "._MOVE" (car obj) "" "0,0" (list deltaX 0.0 0.0))
                        )
                        (setq currentX (+ targetX (caddr obj) distance))
                        (setq i (1+ i))
                    )
                    (command "_.UNDO" "_End")
                    (princ (strcat "\nРаспределено объектов по горизонтали с расстоянием " (rtos distance) " между объектами: " (itoa count)))
                    (sssetfirst nil ss)
                )
                (princ "\nРасстояние не указано.")
            )
        )
        (if ss
            (princ "\nДля распределения нужно выбрать как минимум 2 объекта.")
            (princ "\nОбъекты не выбраны.")
        )
    )
    (princ)
)

;; Распределение по вертикали (одинаковые промежутки) с любым расстоянием
(defun c:RZYD (/ ss count objects sortedObjects distance currentY i obj boundingBox bottomPt topPt objHeight ent deltaY targetY)
    (princ "\nВыберите объекты для распределения по вертикали (одинаковые промежутки): ")
    (setq ss (ssget))
    (if (and ss (> (sslength ss) 1))
        (progn
            (vl-load-com)
            (setq distance (get-distance-with-default "\nУкажите расстояние между объектами (любое значение)"))
            (if (not (null distance))
                (progn
                    (setq count (sslength ss))
                    (setq objects '())
                    (setq i 0)
                    (while (< i count)
                        (setq ent (ssname ss i))
                        (setq boundingBox (getBoundingBox ent))
                        (if boundingBox
                            (progn
                                (setq bottomPt (car boundingBox))
                                (setq topPt (cadr boundingBox))
                                (setq objHeight (- (cadr topPt) (cadr bottomPt)))
                                (setq objects (cons (list ent (cadr bottomPt) objHeight) objects))
                            )
                        )
                        (setq i (1+ i))
                    )
                    (setq sortedObjects (vl-sort objects '(lambda (a b) (< (cadr a) (cadr b)))))
                    (command "_.UNDO" "_Begin")
                    (setq currentY (cadr (car sortedObjects)))
                    (setq i 0)
                    (foreach obj sortedObjects
                        (setq targetY currentY)
                        (setq deltaY (- targetY (cadr obj)))
                        (if (not (equal deltaY 0.0 1e-8))
                            (command "._MOVE" (car obj) "" "0,0" (list 0.0 deltaY 0.0))
                        )
                        (setq currentY (+ targetY (caddr obj) distance))
                        (setq i (1+ i))
                    )
                    (command "_.UNDO" "_End")
                    (princ (strcat "\nРаспределено объектов по вертикали с расстоянием " (rtos distance) " между объектами: " (itoa count)))
                    (sssetfirst nil ss)
                )
                (princ "\nРасстояние не указано.")
            )
        )
        (if ss
            (princ "\nДля распределения нужно выбрать как минимум 2 объекта.")
            (princ "\nОбъекты не выбраны.")
        )
    )
    (princ)
)




;; Функция для сброса сохраненного расстояния
(defun c:RD-RESET ()
    (setq *rd-last-distance* nil)
    (princ "\nСохраненное расстояние для всех команд распределения сброшено.")
    (princ)
)


;; Функция для просмотра сохраненного расстояния
(defun c:RD-SHOW ()
    (princ (strcat "\nТекущее сохраненное расстояние: " 
                   (if (> *rd-last-distance* nil)
                       (rtos *rd-last-distance*)
                       "не установлено")))
    (princ)
)


; ============================================
; ИНФОРМАЦИЯ О КОМАНДАХ
; ============================================

(princ "\n=== ALIGNTOOLS - Команды выравнивания и распределения объектов ===")
(princ "\nОсновные команды:")
(princ "\nALIGNTOOLS или ATOOLS - Вызов диалогового окна")
(princ "\n")
(princ "\nВЫРАВНИВАНИЕ (6 команд):")
(princ "\nAL  - Выравнивание по левому краю")
(princ "\nAR  - Выравнивание по правому краю") 
(princ "\nAT  - Выравнивание по верхнему краю")
(princ "\nAB  - Выравнивание по нижнему краю")
(princ "\nACX - Выравнивание по центру по горизонтали")
(princ "\nACY - Выравнивание по центру по вертикали")
(princ "\n")
(princ "\nРАСПРЕДЕЛЕНИЕ (АВТОМАТИЧЕСКОЕ - 8 команд):")
(princ "\nRLX - Распределить по горизонтали (левый край)")
(princ "\nRRX - Распределить по горизонтали (правый край)")
(princ "\nRTY - Распределить по вертикали (верхний край)")
(princ "\nRBY - Распределить по вертикали (нижний край)")
(princ "\nRCX - Распределить по горизонтали (по центрам)")
(princ "\nRCY - Распределить по вертикали (по центрам)")
(princ "\nRZX - Распределить по горизонтали (одинаковые промежутки)")
(princ "\nRZY - Распределить по вертикали (одинаковые промежутки)")
(princ "\n")
(princ "\nРАСПРЕДЕЛЕНИЕ (С РАССТОЯНИЕМ - 8 команд):")
(princ "\nRLXD - По горизонтали (левый край) с расстоянием")
(princ "\nRRXD - По горизонтали (правый край) с расстоянием")
(princ "\nRTYD - По вертикали (верхний край) с расстоянием")
(princ "\nRBYD - По вертикали (нижний край) с расстоянием")
(princ "\nRCXD - По горизонтали (центры) с расстоянием")
(princ "\nRCYD - По вертикали (центры) с расстоянием")
(princ "\nRZXD - По горизонтали (промежутки) с расстоянием")
(princ "\nRZYD - По вертикали (промежутки) с расстоянием")
(princ "\n")
(princ "\n================================================================")
(princ "\nВсего доступно 22 команды для работы с объектами!")
(princ "\n================================================================")
(princ)
