(defun X2T (elist)   
   (car (cadr (textbox elist )))
)
;----------------------------------------
(defun DXF (code elist)
   (cdr (assoc code elist))
)

;-------------------------------------------------------------
(defun c2_u_ssget ( / ssl nsset temp ed  edmin namemin)
   (setq sset (ssget))
   (setq ssl (sslength sset) 
      nsset (ssadd)
   )
   (print ssl)
   (princ "entities found. ")  
   (princ "\nVerifying the selected entities -- please wait. ")
   (while (> ssl 0)
      (progn
         (setq temp (ssname sset (setq ssl (1- ssl))))
         (setq ed (entget temp))
         (if (= (DXF 0 ed) "TEXT") (ssadd temp nsset))
      )
   )
   (setq ssl (sslength nsset)
      sset nsset
      nsset (ssadd)
   )
   (while (/= (sslength sset) 0)                 ;SAP XEP DOI TUONG
      (setq temp  (ssname sset 0))
      (setq namemin temp )
      (setq edmin (entget namemin))
      (while (> ssl 0)
         (progn
            (setq temp (ssname sset (setq ssl (1- ssl))))
            (setq ed (entget temp))
            (if (<= (cadr (DXF 10 ed)) (cadr (DXF 10 edmin )) ) 
               (progn
                  (setq namemin temp)
                  (setq edmin (entget namemin))               
               )
            ) 
         )
      )
      (ssadd namemin nsset)
      (ssdel namemin sset)
      (setq ssl (sslength sset))
   )
   (setq ssl (sslength nsset)
      sset nsset
      nsset (ssadd)
   )
   (print ssl)
   (princ "TEXT entities found. ")
   (princ)
);defun u_ssget

;-------------------------------------------------------------
(defun c:ARR1 ( / sset ssl temp new old p )
   (c2_u_ssget)
   (setq p (getpoint "\nInput point to left border : " ) )
   (setq ck (getdist "\nInput row height : " ) )
   (setq ssl (sslength sset))       
   (while (> ssl 0)
      (progn 
         (setq temp (ssname sset (setq ssl (1- ssl)))
            ed (entget temp)
            old (cons 10 (DXF 10 ed))            
            new (cons 10 p)
            ed (subst new old ed)           
            p (list (car p) (- (cadr p) ck) 0.0 )
         )
         (entmod ed)  
      )
   )
   (princ)
);defun
;-------------------------------------------------------------
(defun c:FT ( / sset ssl temp new old )   
   (c2_u_ssget)
   (setq ssl (sslength sset)
      ssl1 ssl  
   )     
   (setq temp (ssname sset (- ssl 1) )
      ed (entget temp)
      point (DXF 10 ed)  
   )   
   (setq newlength (getdist  point "\nInput new length of text  : " ) )     
   (while (> ssl 0)
      (progn 
         (setq temp (ssname sset (setq ssl (1- ssl)))
            ed (entget temp)
            oldlength (/ (X2T ed) (DXF 41 ed))
            width (/ newlength oldlength)
            old (cons 41 (DXF 41 ed))     
         )
         (if (or (<= width  0.8 ) (>= width 1.2 ))              
            (progn
               (setq new old)
               (print " This line too long or short : ")
               (princ)
               (princ (- ssl1 ssl))
            )
            (setq new (cons 41 width))            
         )
         (setq ed (subst new old ed))         
         (entmod ed)  
      )
   )
   (princ)
);defun
;--------------------------------------------
(defun c:ARR ( / kieu)
   (setq kieu (getstring "\n Arr / Ft (Arr) : "))
   (if (= kieu "") (setq kieu "a"))
   (if (or (= kieu "A") (= kieu "a")) (c:ARR1))
   (if (or (= kieu "F") (= kieu "f")) (c:FT))
   (if (or (/= kieu "A") (/= kieu "a") (/= kieu "F") (/= kieu "f")) (princ "\ninvalid key"))
)
(prompt "\nARR : To ARRANGE TEXT ")
