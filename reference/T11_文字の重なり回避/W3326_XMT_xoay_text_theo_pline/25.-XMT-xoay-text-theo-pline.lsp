(defun c:XMT (/ oldos sst1 pl obj p0 par etxt ans ans1 k p goc kt gocch kp kc pc pl1 pl2 spc)
(vl-load-com)
(princ "\nPhong tu van giao thong - Cty TNHH TVXD TS Q.Binh")
(setq cur_lay (getvar "clayer" ))
(setq oldos (getvar "osmode"))
(command "undo" "be")
(setvar "osmode" 0)
(command "-layer" "new" "line_coc" "color" "1" "line_coc" "")
(command "-layer" "set" "line_coc" "")
(Princ "\nChon tap hop text can xoay va move")
(setq sst (acet-ss-to-list (ssget (list (cons 0 "text")))))
(setq ssl (ssget "X" (list (cons 8 "line_coc") (cons 0 "LINE"))))
(setq pl (car (entsel "\n Chon polyline dinh huong")))
(initget "c k C K")
(setq ans1 (getkword "\n Move Text so voi Pline [C / K]"))
(if (or(= ans1 "c")(= ans1 "C")(not ans1))
(setq k (getreal "\n Nhap khoang cach text so voi pline: ")))
(initget "c k C K")
(setq ans (getkword "\n Xoay text theo huong Pline [C / K]"))
(initget "c k C K")
(setq ans2 (getkword "\n Ve line theo chu [C / K]"))
(if (/= nil ssl) (acet-ss-entdel ssl))
(setq obj (vlax-ename->vla-object pl))
(setq spc (vla-get-ModelSpace (vla-get-ActiveDocument(vlax-get-Acad-Object))))
(setq h (cdr (assoc 40 (entget (nth 0 sst)))))
(foreach txt sst
(setq p0 (if (or (/= (cdr (assoc 72 (setq etxt (entget txt)))) 0) (/= (cdr (assoc 73 etxt)) 0)) 
(vlax-curve-getclosestpointto obj (cdr (assoc 11 etxt)) T)                   
(vlax-curve-getclosestpointto obj (cdr (assoc 10 etxt)) T))       
par (vlax-curve-getparamatpoint obj p0)        
)
(setq p (if (or (/= (cdr (assoc 72 etxt)) 0) (/= (cdr (assoc 73 etxt)) 0))
                        (cdr (assoc 11 etxt)) (cdr (assoc 10 etxt))))
(setq goc (angle '(0 0 0) (vlax-curve-getFirstDeriv obj par)))
(if (or(= ans "c")(= ans "C")(not ans))
(setq etxt (subst (cons 50 (FixTextAngle goc)) (assoc 50 etxt) etxt)))
(if (or(= ans1 "c")(= ans1 "C")(not ans1))
(progn
(setq kt (sin (- (angle p0 p) goc)))
(if (>= kt 0)
(setq gocch (+ goc (* (/ pi 2) 3))) 
(setq gocch (+ goc (/ pi 2))))
(setq kp (distance p0 p))
(setq kc (- kp k))
(setq pc (polar p gocch kc))
(setq pl1 (polar pc gocch h))
(setq pl2 (polar pl1 gocch  h))
(if (= (+ (cdr (assoc 72 etxt)) (cdr (assoc 73 etxt))) 0)
(setq etxt (subst (cons 10 pc) (assoc 10 etxt) etxt))
(setq etxt (subst (cons 11 pc) (assoc 11 etxt) etxt)))))
(entmod etxt)
(if (or(= ans2 "c")(= ans2 "C")(not ans2))
(vla-addline spc (vlax-3d-point pl1) (vlax-3d-point pl2)))
;(entmakex (list '(0 . "LINE") (cons 10 pc) (cons 11 p)))
)
(command "undo" "e")
(setvar "MODEMACRO" "**Phong Tu Van Giao Thong II** huunhanltqb@yahoo.com")
(setvar "osmode" oldos)
(setvar "clayer" cur_lay)
(princ))
;;;;;;;;;;;;;;;;;;;;;;;;;;;;;;;;   
(defun MakeLine (PT1 PT2 Linetype LTScale Layer Color xdata)	
(entmakex (list '(0 . "LINE") 
		(cons 8 (if Layer Layer (getvar "Clayer")))
		(cons 6 (if Linetype Linetype "bylayer"))
		(cons 48 (if LTScale LTScale 1))
		(cons 62 (if Color Color 256))	
		(cons 10 PT1)	
		(cons 11 PT2)
		)));end  
(defun FixTextAngle  (ang)
  (cond ((and (> ang (* 0.5 pi)) (< ang (* 1.5 pi))) (setq ang (+ ang pi)))
        ((equal ang (* 1.5 pi) 1e-6) (setq ang (* 0.5 pi))))
  ang)
