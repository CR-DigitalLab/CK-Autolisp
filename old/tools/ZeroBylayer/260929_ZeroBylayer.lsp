;;----------------------------------------------------------------------------;;
;; 【ご利用についてのお願い】
;; このコードは、作業効率化を目的として開発されたものです。
;; 個人利用や業務効率化のためにご活用いただけると幸いです。
;;
;; 【著作権および利用制限について】
;; 本スクリプトはCHIKOが著作権を保有しており、著作権によって保護されています。
;; 著作権表示は削除しないでください。
;; ご購入者様の個人利用、および所属する組織内での業務利用に限りご使用いただけます。
;; 本スクリプトの全部または一部を、許可なく複製、転載、再配布、販売することを禁止します。
;;----------------------------------------------------------------------------;;
(defun c:ZeroByLayer ()
  (setvar "CMDECHO" 0)
  
  ;; Undo記録の開始
  (command "_.UNDO" "_Begin")
  
  ;; 現在の画層を「0」に設定
  (setvar "CLAYER" "0")
  
  ;; 各プロパティを「ByLayer」に設定
  (setvar "CECOLOR" "BYLAYER")   ; 色（文字列）
  (setvar "CELTYPE" "ByLayer")   ; 線種（文字列）
  (setvar "CELWEIGHT" -1)        ; 線の太さ（整数：-1 = ByLayer）
  (setvar "CETRANSPARENCY" -1)   ; 透過性（整数：-1 = ByLayer）
  
  ;; Undo記録の終了
  (command "_.UNDO" "_End")
  
  (setvar "CMDECHO" 1)
  (princ "\n現在の画層を「0」にし、作成プロパティをすべて「ByLayer」にリセットしました。")
  (princ)
)

;; ショートカットコマンド：ZB
(defun c:ZB ()
  (c:ZeroByLayer)
  (princ)
)
