;;------------------------------------------------------------------------------------;;
;; 【利用制限について】
;; 本スクリプトの全部または一部を、許可なく複製、転載、再配布、販売することを禁止します。
;;------------------------------------------------------------------------------------;;
(defun c:CADSOZAI ()
  (command "_.browser" "https://cad-freed-rawingsamples.com/sitemaps/")
  (princ) 
)

(defun c:TANUKISAN ()
  (c:CADSOZAI)
)

(princ "\n 「CADSOZAI」でCAD素材.comが開けます！")
(princ)
