;;; ======================================================================================================================
;;; 【自動実行の設定方法 (スタートアップ登録)】
;;;  図面を開くたびに自動でこのLISPを適用するには、以下の手順を行ってください。
;;;
;;;  1. AutoCAD上で「APPLOAD」コマンドを実行します。
;;;     (キーボードで APPLOAD と入力して Enterキー)
;;;
;;;  2. ダイアログ画面の右下（またはスタートアップ登録という枠内）にある
;;;     「内容」ボタンをクリックします。
;;;
;;;  3. 開いた画面で「追加」ボタンをクリックします。
;;;
;;;  4. 保存したこのファイル (.lsp) を選択して「開く」をクリックします。
;;;
;;;  5. リストに追加されたことを確認し、「閉じる」ボタンですべての画面を閉じます。
;;;
;;;  以上で設定完了です。
;;;  次回から図面を開くたびに、自動的にこのLISPが実行されHPDRAWORDER を自動で「最背面 (1)」に設定します。
;;;  ※なお、このLISPのファイル名を変えてしまったり、場所を他の所に変えてしまうと自動で読み込めなくなるのでご注意ください。
;;;   
;;; ======================================================================================================================

;;; HPDRAWORDER1 ver2（2026-09-30）
;;;   ・文字コードを ANSI（Shift-JIS）に変更（UTF-8 では AutoCAD のバージョンによって日本語が文字化けするため）
;;;   ※動き（図面を開くたびに HPDRAWORDER を 1 にする）は ver1 と同じ

(if (getvar "HPDRAWORDER")
  (setvar "HPDRAWORDER" 1)
)

(princ)
